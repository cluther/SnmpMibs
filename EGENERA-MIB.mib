--
-- egenera.v2.mib
--
-- Copyright 2000 Egenera, Inc. All rights reserved.
-- This software is the proprietary information of Egenera, Inc.
--
-- This MIB exposes attributes of Egenera BladeFrames in the Egenera PAN.
--

EGENERA-MIB DEFINITIONS ::= BEGIN

IMPORTS

    MODULE-IDENTITY, OBJECT-TYPE, NOTIFICATION-TYPE,
    TimeTicks, Counter32, Gauge32, Integer32, IpAddress,
    enterprises
        FROM SNMPv2-SMI

    MODULE-COMPLIANCE, OBJECT-GROUP
        FROM SNMPv2-CONF

    TEXTUAL-CONVENTION, DisplayString, PhysAddress, TruthValue
        FROM SNMPv2-TC;


egenera MODULE-IDENTITY
    LAST-UPDATED
            "201104010900Z"

    ORGANIZATION
            "Egenera, Inc."

    CONTACT-INFO
            "EES

             Egenera, Inc.
             165 Forest Street
             Marlboro, MA 01752

             phone: 1 866 301 3117
             email: support@egenera.com"

    DESCRIPTION
            "This MIB exposeses statistics and controls for Egenera
            BladeFrames."


    REVISION
            "201104010900Z"
    DESCRIPTION
	    "Addition of Java File and Memory cBlade statistics."

    REVISION
            "200911010900Z"
    DESCRIPTION
	    "Addition of Hypervisor Group traps."


    REVISION
            "200508300900Z"
    DESCRIPTION
            "Addition of Power Input Module (PIM) table and traps.
             Support for cBlade Etherenet Link and REth Membership
             state, and REth State."


    REVISION
            "200401150900Z"
    DESCRIPTION
            "Enchancements for the 'New Logical Model' (Picard Release)
             Including new traps and deprecated traps so that every user
             visible event in the NLM is supported by a trap.

             Also introduced additional application visibility in the MIB
             to support new application event/traps."


    REVISION
            "200309290900Z"

    DESCRIPTION
            "Set of traps expanded.  The goal is to provide a trap for each
             user visible event type.  Initially, traps only added for sev
             1-3 event types not previously supported by traps.

             Additionally, traps defined due to early requirements documents
             that no longer have an event type to drive the trap have been
             identified as deprecated in the trap definitions."


    REVISION
            "200302201100Z"

    DESCRIPTION
            "New definitions for BladeFrame ES and SMI error corrections."


    REVISION
            "200010050900Z"

    DESCRIPTION
            "Initial version."

        ::=     { enterprises 7559 }


-- Egenera proprietary OIDs

management      OBJECT IDENTIFIER ::= { egenera 1 }
thirdParty      OBJECT IDENTIFIER ::= { egenera 100 }
-- experimental    OBJECT IDENTIFIER ::= { egenera 200 }
adminInfo       OBJECT IDENTIFIER ::= { egenera 1000 }

panManager      OBJECT IDENTIFIER ::= { management 1 }



-- panManager group
--   Contains information about the Egenera PAN Manager agent.


panManagerPANName OBJECT-TYPE
    SYNTAX      DisplayString
    MAX-ACCESS  read-only
    STATUS      current
    DESCRIPTION
            "A textual string identifying the Egenera PAN represented by
            this PAN Manager agent."

        ::=     { panManager 1 }


panManagerId OBJECT-TYPE
    SYNTAX      DisplayString
    MAX-ACCESS  read-only
    STATUS      current
    DESCRIPTION
            "A textual string uniquely identifying the PAN Manager agent."

        ::=     { panManager 2 }


panManagerHostname OBJECT-TYPE
    SYNTAX      DisplayString
    MAX-ACCESS  read-only
    STATUS      current
    DESCRIPTION
            "A textual string identifying the hostname on which the
            master PAN Manager agent is running."

        ::=     { panManager 3 }


panManagerAgentType OBJECT-TYPE
    SYNTAX      DisplayString
    MAX-ACCESS  read-only
    STATUS      current
    DESCRIPTION
            "An OID representing the agent type of the agent.
            Possible values include PAN, LPAN, and BladeFrame.

            NOTE: BladeFrame agent types are deprecated and subject to removal."

        ::=     { panManager 4 }




agentTypes      OBJECT IDENTIFIER ::= { panManager 5 }

pan             OBJECT IDENTIFIER ::= { agentTypes 1 }
lPan            OBJECT IDENTIFIER ::= { agentTypes 2 }
bladeFrame      OBJECT IDENTIFIER ::= { agentTypes 3 }



roles           OBJECT IDENTIFIER ::= { panManager 9 }
panRoles        OBJECT IDENTIFIER ::= { roles 1 }
bladeFrameRoles OBJECT IDENTIFIER ::= { roles 2 }
lpanRoles       OBJECT IDENTIFIER ::= { roles 3 }


-- pan roles

panRoleTable    OBJECT-TYPE
    SYNTAX      SEQUENCE OF PanRoleEntry
    MAX-ACCESS  not-accessible
    STATUS      current
    DESCRIPTION
            "A table of PAN panRoles."

        ::=     { panRoles 1 }


panRoleEntry OBJECT-TYPE
    SYNTAX      PanRoleEntry
    MAX-ACCESS  not-accessible
    STATUS      current
    DESCRIPTION
            "A panRoleEntry contains general information about each
            PAN Role."

    INDEX       { panRoleIndex }
        ::=     { panRoleTable 1 }


PanRoleEntry ::=
    SEQUENCE {
        panRoleIndex
            Integer32,
        panRoleName
            DisplayString,
        panRoleDescription
            DisplayString
    }

panRoleIndex OBJECT-TYPE
    SYNTAX      Integer32 (1..2147483647)
    MAX-ACCESS  read-only
    STATUS      current
    DESCRIPTION
            "An integer value uniquely identifying the PAN role:
                1: Administrator, 2: Operator, 3: Monitor"

        ::=     { panRoleEntry 1 }


panRoleName OBJECT-TYPE
    SYNTAX      DisplayString
    MAX-ACCESS  read-only
    STATUS      current
    DESCRIPTION
            "The human readable name of the PAN role."

        ::=     { panRoleEntry 2 }


panRoleDescription OBJECT-TYPE
    SYNTAX      DisplayString
    MAX-ACCESS  read-only
    STATUS      current
    DESCRIPTION
            "The human readable description of the PAN role."

        ::=     { panRoleEntry 3 }



-- BladeFrame roles

bladeFrameRoleTable  OBJECT-TYPE
    SYNTAX      SEQUENCE OF BladeFrameRoleEntry
    MAX-ACCESS  not-accessible
    STATUS      current
    DESCRIPTION
            "A table of BladeFrame roles.

            NOTE: BladeFrame roles are deprecated and subject to removal."

        ::=     { bladeFrameRoles 1 }


bladeFrameRoleEntry OBJECT-TYPE
    SYNTAX      BladeFrameRoleEntry
    MAX-ACCESS  not-accessible
    STATUS      current
    DESCRIPTION
            "A bladeFrameRoleEntry contains general information about each
            BladeFrame Role.

            NOTE: BladeFrame roles are deprecated and subject to removal."

    INDEX       { bladeFrameIndex, bladeFrameRoleIndex }
        ::=     { bladeFrameRoleTable 1 }


BladeFrameRoleEntry ::=
    SEQUENCE {
        bladeFrameRoleIndex
            Integer32,
        bladeFrameRoleBladeFrameIndex
            Integer32,
        bladeFrameRoleName
            DisplayString,
        bladeFrameRoleDescription
            DisplayString
    }

bladeFrameRoleIndex OBJECT-TYPE
    SYNTAX      Integer32 (1..2147483647)
    MAX-ACCESS  read-only
    STATUS      current
    DESCRIPTION
            "An integer value uniquely identifying the BladeFrame role:
                1: Administrator, 2: Operator, 3: Monitor

                NOTE: BladeFrame roles are deprecated and subject to removal."

        ::=     { bladeFrameRoleEntry 1 }


bladeFrameRoleBladeFrameIndex OBJECT-TYPE
    SYNTAX      Integer32
    MAX-ACCESS  read-only
    STATUS      current
    DESCRIPTION
            "The bladeFrameIndex value of the BladeFrame that this role applies
            to.

            NOTE: BladeFrame roles are deprecated and subject to removal."

        ::=     { bladeFrameRoleEntry 2 }


bladeFrameRoleName OBJECT-TYPE
    SYNTAX      DisplayString
    MAX-ACCESS  read-only
    STATUS      current
    DESCRIPTION
            "The human readable name of the BladeFrame role.

            NOTE: BladeFrame roles are deprecated and subject to removal."

        ::=     { bladeFrameRoleEntry 3 }


bladeFrameRoleDescription OBJECT-TYPE
    SYNTAX      DisplayString
    MAX-ACCESS  read-only
    STATUS      current
    DESCRIPTION
            "The human readable description of the BladeFrame role.

            NOTE: BladeFrame roles are deprecated and subject to removal."

        ::=     { bladeFrameRoleEntry 4 }


-- LPAN Roles

lpanRoleTable  OBJECT-TYPE
    SYNTAX      SEQUENCE OF LpanRoleEntry
    MAX-ACCESS  not-accessible
    STATUS      current
    DESCRIPTION
            "A table of LPAN roles."

        ::=     { lpanRoles 1 }

lpanRoleEntry OBJECT-TYPE
    SYNTAX      LpanRoleEntry
    MAX-ACCESS  not-accessible
    STATUS      current
    DESCRIPTION
            "A lpanRoleEntry contains general information about each
            LPAN Role."

    INDEX       { lPanIndex,  lpanRoleIndex }
        ::=     { lpanRoleTable 1 }


LpanRoleEntry ::=
    SEQUENCE {
        lpanRoleIndex
            Integer32,
        lpanRoleLpanIndex
            Integer32,
        lpanRoleName
            DisplayString,
        lpanRoleDescription
            DisplayString
    }

lpanRoleIndex OBJECT-TYPE
    SYNTAX      Integer32 (1..2147483647)
    MAX-ACCESS  read-only
    STATUS      current
    DESCRIPTION
            "An integer value uniquely identifying the LPAN role:
                1: Administrator, 2: Operator, 3: Monitor"

        ::=     { lpanRoleEntry 1 }


lpanRoleLpanIndex OBJECT-TYPE
    SYNTAX      Integer32
    MAX-ACCESS  read-only
    STATUS      current
    DESCRIPTION
            "The lpanIndex of value of the LPAN that this role applies to."

        ::=     { lpanRoleEntry 2 }


lpanRoleName OBJECT-TYPE
    SYNTAX      DisplayString
    MAX-ACCESS  read-only
    STATUS      current
    DESCRIPTION
            "The human readable name of the LPAN role."

        ::=     { lpanRoleEntry 3 }


lpanRoleDescription OBJECT-TYPE
    SYNTAX      DisplayString
    MAX-ACCESS  read-only
    STATUS      current
    DESCRIPTION
            "The human readable description of the BladeFrame role."

        ::=     { lpanRoleEntry 4 }



-- panUsers group
--    Countains information about authorized users

userTable  OBJECT-TYPE
    SYNTAX      SEQUENCE OF UserEntry
    MAX-ACCESS  not-accessible
    STATUS      current
    DESCRIPTION
            "A table of PAN users."

        ::=     { panManager 10 }


userEntry OBJECT-TYPE
    SYNTAX      UserEntry
    MAX-ACCESS  not-accessible
    STATUS      current
    DESCRIPTION
            "A UserEntry contains general information about each
            user in the Egenera PAN."

    INDEX       { userIndex }
        ::=     { userTable 1 }


UserEntry ::=
    SEQUENCE {
        userIndex
            Integer32,
        userName
            DisplayString,
        userFullName
            DisplayString,
        userTitle
            DisplayString,
        userDescription
            DisplayString,
        userDepartment
            DisplayString,
        userEmail
            DisplayString
    }


userIndex OBJECT-TYPE
    SYNTAX      Integer32 (1..2147483647)
    MAX-ACCESS  read-only
    STATUS      current
    DESCRIPTION
            "An integer value uniquely identifying the user."

        ::=     { userEntry 1 }


userName OBJECT-TYPE
    SYNTAX      DisplayString
    MAX-ACCESS  read-only
    STATUS      current
    DESCRIPTION
            "The username for this user."

        ::=     { userEntry 2 }


userFullName OBJECT-TYPE
    SYNTAX      DisplayString
    MAX-ACCESS  read-only
    STATUS      current
    DESCRIPTION
            "The full name for this user."

        ::=     { userEntry 3 }


userTitle OBJECT-TYPE
    SYNTAX      DisplayString
    MAX-ACCESS  read-only
    STATUS      current
    DESCRIPTION
            "The title of this user."

        ::=     { userEntry 4 }


userDescription OBJECT-TYPE
    SYNTAX      DisplayString
    MAX-ACCESS  read-only
    STATUS      current
    DESCRIPTION
            "The description of this user."

        ::=     { userEntry 5 }


userDepartment OBJECT-TYPE
    SYNTAX      DisplayString
    MAX-ACCESS  read-only
    STATUS      current
    DESCRIPTION
            "The department of this user."

        ::=     { userEntry 6 }


userEmail OBJECT-TYPE
    SYNTAX      DisplayString
    MAX-ACCESS  read-only
    STATUS      current
    DESCRIPTION
            "The email address for this user."

        ::=     { userEntry 7 }


userRoleTable  OBJECT-TYPE
    SYNTAX      SEQUENCE OF UserRoleEntry
    MAX-ACCESS  not-accessible
    STATUS      current
    DESCRIPTION
            "A table indicating the set of roles that each user belongs
            to.  There are three types of roles; Administrator, Operator,
            and Monitor.  Each of these roles exists for each LPAN, for
            each BladeFrame, and for the PAN.

            NOTE: BladeFrame roles are deprecated and subject to removal."

        ::=     { panManager 12 }


userRoleEntry OBJECT-TYPE
    SYNTAX      UserRoleEntry
    MAX-ACCESS  not-accessible
    STATUS      current
    DESCRIPTION
            "Each UserRoleEntry indicates a role that a user belongs to."

    INDEX       { userIndex, userRoleIndex }
        ::=     { userRoleTable 1 }


UserRoleEntry ::=
    SEQUENCE {
        userRoleUserIndex
            Integer32,
        userRoleIndex
            Integer32,
        userRoleRoleOid
            OBJECT IDENTIFIER
    }


userRoleUserIndex OBJECT-TYPE
    SYNTAX      Integer32 (1..2147483647)
    MAX-ACCESS  read-only
    STATUS      current
    DESCRIPTION
            "The userIndex of the user that belongs to this role."

        ::=     { userRoleEntry 1 }


userRoleIndex OBJECT-TYPE
    SYNTAX      Integer32 (1..2147483647)
    MAX-ACCESS  read-only
    STATUS      current
    DESCRIPTION
            "An integer index identifying this user/role relationship."

        ::=     { userRoleEntry 2 }


userRoleRoleOid OBJECT-TYPE
    SYNTAX      OBJECT IDENTIFIER
    MAX-ACCESS  read-only
    STATUS      current
    DESCRIPTION
            "The fully qualified index OID of the role assigned to this user.
            The OID will uniquely identify a panRoleIndex, bladeFrameRoleIndex,
            or lpanRoleIndex instance.

            NOTE: BladeFrame roles are deprecated and subject to removal."

        ::=     { userRoleEntry 3 }


-- bladeFrames group
--   Contains information about BladeFrames in the Egenera PAN.

PowerStatusType ::= TEXTUAL-CONVENTION
    STATUS      current
    DESCRIPTION
            "Describes power status for blades."
    SYNTAX INTEGER {
        on(1),
        off(2),
        undefined(999)
    }

HealthStatusType ::= TEXTUAL-CONVENTION
    STATUS      current
    DESCRIPTION
            "Describes health status for blades."
    SYNTAX INTEGER {
        green(1),
        yellow(2),
        red(3),
        undefined(999)
    }

PlatformRole ::= TEXTUAL-CONVENTION
    STATUS      current
    DESCRIPTION
            "Describes roles of BladeFrames and cBlades in the PAN."
    SYNTAX INTEGER {
        pan-bf-master(1),
        pan-bf-slave(2),
        bf-master(3),
        bf-slave(4),
        unknown(999)
    }

bladeFrames     OBJECT IDENTIFIER ::= { management 2 }

bladeFramesInPAN OBJECT-TYPE
    SYNTAX      Integer32
    MAX-ACCESS  read-only
    STATUS      current
    DESCRIPTION
            "The number of BladeFrames in the Egenera PAN."

        ::=     { bladeFrames 1 }


bladeFrameTable  OBJECT-TYPE
    SYNTAX      SEQUENCE OF BladeFrameEntry
    MAX-ACCESS  not-accessible
    STATUS      current
    DESCRIPTION
            "A list of BladeFrame entries.  The number of entries is given by
            the value of bladeFramesInPAN.  This is a sparse table."

        ::=     { bladeFrames 2 }


bladeFrameEntry OBJECT-TYPE
    SYNTAX      BladeFrameEntry
    MAX-ACCESS  not-accessible
    STATUS      current
    DESCRIPTION
            "A BladeFrame entry contains general information about each
            BladeFrame in the Egenera PAN."

    INDEX       { bladeFrameIndex }
        ::=     { bladeFrameTable 1 }


BladeFrameEntry ::=
    SEQUENCE {
        bladeFrameIndex
            Integer32,
        bladeFrameName
            DisplayString,
        bladeFrameHealthStatus
            HealthStatusType,
        bladeFrameUpTime
            TimeTicks,
        bladeFrameNumControlBlades
            Integer32,
        bladeFrameMaxControlBlades
            Integer32,
        bladeFrameNumSwitchBlades
            Integer32,
        bladeFrameMaxSwitchBlades
            Integer32,
        bladeFrameNumProcessingBlades
            Integer32,
        bladeFrameMaxProcessingBlades
            Integer32,
        bladeFrameType
            DisplayString,
        bladeFramePIMVoltageTrigger
            Integer32,
        bladeFrameRole
            PlatformRole
    }


bladeFrameIndex OBJECT-TYPE
    SYNTAX      Integer32 (1..2147483647)
    MAX-ACCESS  read-only
    STATUS      current
    DESCRIPTION
            "An integer value uniquely identifying the BladeFrame."

        ::=     { bladeFrameEntry 1 }


bladeFrameName OBJECT-TYPE
    SYNTAX      DisplayString
    MAX-ACCESS  read-only
    STATUS      current
    DESCRIPTION
            "A textual string identifying the BladeFrame."

        ::=     { bladeFrameEntry 2 }


bladeFrameHealthStatus OBJECT-TYPE
    SYNTAX      HealthStatusType
    MAX-ACCESS  read-only
    STATUS      current
    DESCRIPTION
            "An indication of the health of the BladeFrame."

        ::=     { bladeFrameEntry 3 }


bladeFrameUpTime OBJECT-TYPE
    SYNTAX      TimeTicks
    MAX-ACCESS  read-only
    STATUS      current
    DESCRIPTION
            "The amount of time that the BladeFrame has been up."

        ::=     { bladeFrameEntry 4 }


bladeFrameNumControlBlades OBJECT-TYPE
    SYNTAX      Integer32
    MAX-ACCESS  read-only
    STATUS      current
    DESCRIPTION
            "The number of cBlades present in the BladeFrame."

        ::=     { bladeFrameEntry 5 }


bladeFrameMaxControlBlades OBJECT-TYPE
    SYNTAX      Integer32
    MAX-ACCESS  read-only
    STATUS      current
    DESCRIPTION
            "The maximum number of cBlades that may be present in the
            BladeFrame."

        ::=     { bladeFrameEntry 6 }


bladeFrameNumSwitchBlades OBJECT-TYPE
    SYNTAX      Integer32
    MAX-ACCESS  read-only
    STATUS      current
    DESCRIPTION
            "The number of sBlades contained in the BladeFrame."

        ::=     { bladeFrameEntry 7 }


bladeFrameMaxSwitchBlades OBJECT-TYPE
    SYNTAX      Integer32
    MAX-ACCESS  read-only
    STATUS      current
    DESCRIPTION
            "The maximum number of sBlades that may be contained in the
            BladeFrame."

        ::=     { bladeFrameEntry 8 }


bladeFrameNumProcessingBlades OBJECT-TYPE
    SYNTAX      Integer32
    MAX-ACCESS  read-only
    STATUS      current
    DESCRIPTION
            "The number of pBlades contained in the BladeFrame."

        ::=     { bladeFrameEntry 9 }


bladeFrameMaxProcessingBlades OBJECT-TYPE
    SYNTAX      Integer32
    MAX-ACCESS  read-only
    STATUS      current
    DESCRIPTION
            "The maximum number of pBlades that may be contained in
            the BladeFrame."

        ::=     { bladeFrameEntry 10 }


bladeFrameType OBJECT-TYPE
    SYNTAX      DisplayString
    MAX-ACCESS  read-only
    STATUS      current
    DESCRIPTION
            "The type of BladeFrame managed by this agent."

        ::=     { bladeFrameEntry 11 }



bladeFramePIMVoltageTrigger OBJECT-TYPE
    SYNTAX      Integer32
    MAX-ACCESS  read-only
    STATUS      current
    DESCRIPTION
            "If the BladeFrame is equiped with PIMs, this column
            will represent the PIM voltage threshold for PIM
            power failover"

        ::=     { bladeFrameEntry 12 }


bladeFrameRole OBJECT-TYPE
    SYNTAX      PlatformRole
    MAX-ACCESS  read-only
    STATUS      current
    DESCRIPTION
            "The role of this BladeFrame in the PAN; either pan-bf-master(1)
            or bf-master(3)"

        ::=     { bladeFrameEntry 13 }



--
-- blades group (cBlades, sBlades, & pBlades)
--

blades      OBJECT IDENTIFIER ::= { bladeFrames 3 }


-- cBlades group

cBlades   OBJECT IDENTIFIER ::= { blades 1 }

-- cBlade table
-- The cBlade table contains information about cBlades in
-- BladeFrames.

cBladeTable  OBJECT-TYPE
    SYNTAX      SEQUENCE OF CBladeEntry
    MAX-ACCESS  not-accessible
    STATUS      current
    DESCRIPTION
            "A list of cBlade entries conaining information for Control
            Blades in the Egenera PAN."

        ::=     { cBlades 1 }


cBladeEntry OBJECT-TYPE
    SYNTAX      CBladeEntry
    MAX-ACCESS  not-accessible
    STATUS      current
    DESCRIPTION
            "A cBlade entry contains information for cBlades in
            the Egenera PAN."

    INDEX       { bladeFrameIndex, cBladeIndex }
        ::=     { cBladeTable 1 }


CBladeEntry ::=
    SEQUENCE {
        cBladeIndex
            Integer32,
        cBladeFrameIndex
            Integer32,
        cBladeName
            DisplayString,
        cBladeSerialNumber
            DisplayString,
        cBladePartNumber
            DisplayString,
        cBladePowerStatus
            PowerStatusType,
        cBladePowerSupply
            DisplayString,
        cBladeMasterStatus
            TruthValue,
        cBladeActiveStatus
            TruthValue,
        cBladeEnabledStatus
            TruthValue,
        cBladeSelectedStatus
            TruthValue,
        cBladeRecognizedStatus
            TruthValue,
        cBladeHealthStatus
            HealthStatusType,
        cBladeUpTime
            TimeTicks,
        cBladeSwitchPowerStatus
            PowerStatusType,
        cBladeRole
            PlatformRole
    }

cBladeIndex OBJECT-TYPE
    SYNTAX      Integer32 (1..2147483647)
    MAX-ACCESS  read-only
    STATUS      current
    DESCRIPTION
            "An integer value uniquely identifying the cBlade within
            the BladeFrame. This corresponds to the physical location of the
            cBlade within the BladeFrame."

        ::=     { cBladeEntry 1 }


cBladeFrameIndex OBJECT-TYPE
    SYNTAX      Integer32 (1..2147483647)
    MAX-ACCESS  read-only
    STATUS      current
    DESCRIPTION
            "An integer value identifying the bladeFrameIndex value of the
            Blade Frame that hosts this cBlade."

        ::=     { cBladeEntry 2 }


cBladeName OBJECT-TYPE
    SYNTAX      DisplayString
    MAX-ACCESS  read-only
    STATUS      current
    DESCRIPTION
            "A textual string identifying cBlade."

        ::=     { cBladeEntry 3 }


cBladeSerialNumber OBJECT-TYPE
    SYNTAX      DisplayString
    MAX-ACCESS  read-only
    STATUS      current
    DESCRIPTION
            "Describes the serial number of this cBlade."

        ::=     { cBladeEntry 4 }


cBladePartNumber OBJECT-TYPE
    SYNTAX      DisplayString
    MAX-ACCESS  read-only
    STATUS      current
    DESCRIPTION
            "Describes the part number of this cBlade."

        ::=     { cBladeEntry 5 }


cBladePowerStatus OBJECT-TYPE
    SYNTAX      PowerStatusType
    MAX-ACCESS  read-only
    STATUS      current
    DESCRIPTION
            "The power status of the cBlade."

        ::=     { cBladeEntry 6 }


cBladePowerSupply OBJECT-TYPE
    SYNTAX      DisplayString
    MAX-ACCESS  read-only
    STATUS      current
    DESCRIPTION
            "The name of the power supply used by this cBlade."

        ::=     { cBladeEntry 7 }


cBladeMasterStatus OBJECT-TYPE
    SYNTAX      TruthValue
    MAX-ACCESS  read-only
    STATUS      current
    DESCRIPTION
            "Indicates whether or this cBlade is the PAN Master or a slave."

        ::=     { cBladeEntry 8 }


cBladeActiveStatus OBJECT-TYPE
    SYNTAX      TruthValue
    MAX-ACCESS  read-only
    STATUS      current
    DESCRIPTION
            "Indicates whether or not the cBlade is active."

        ::=     { cBladeEntry 9 }


cBladeEnabledStatus OBJECT-TYPE
    SYNTAX      TruthValue
    MAX-ACCESS  read-only
    STATUS      current
    DESCRIPTION
            "Indicates whether the cBlade is enabled or disabled."

        ::=     { cBladeEntry 10 }


cBladeSelectedStatus OBJECT-TYPE
    SYNTAX      TruthValue
    MAX-ACCESS  read-only
    STATUS      current
    DESCRIPTION
            "Indicates whether the cBlade is selected."

        ::=     { cBladeEntry 11 }


cBladeRecognizedStatus OBJECT-TYPE
    SYNTAX      TruthValue
    MAX-ACCESS  read-only
    STATUS      current
    DESCRIPTION
            "Indicates whether the blade has been recognized by the PAN Manager."

        ::=     { cBladeEntry 12 }


cBladeHealthStatus OBJECT-TYPE
    SYNTAX      HealthStatusType
    MAX-ACCESS  read-only
    STATUS      current
    DESCRIPTION
            "An indication of the health of the BladeFrame."

        ::=     { cBladeEntry 13 }


cBladeUpTime OBJECT-TYPE
    SYNTAX      TimeTicks
    MAX-ACCESS  read-only
    STATUS      current
    DESCRIPTION
            "The amount of time that the BladeFrame has been up."

        ::=     { cBladeEntry 14 }


cBladeSwitchPowerStatus OBJECT-TYPE
    SYNTAX      PowerStatusType
    MAX-ACCESS  read-only
    STATUS      current
    DESCRIPTION
            "Indicates the power status of the daughter switch card for cBlade ES blades
            in the BladeFrame ES.  This object does not appear on non BladeFrame ES
            systems."

        ::=     { cBladeEntry 15 }


cBladeRole OBJECT-TYPE
    SYNTAX      PlatformRole
    MAX-ACCESS  read-only
    STATUS      current
    DESCRIPTION
            "Indicates the role of the cBlade in the PAN."

        ::=     { cBladeEntry 16 }




-- cBlade SystemMonitor


-- contains runtime statistics for each cBlade.  This table is present when
-- the Egenera management agent is running on the cBlade, and statistic
-- collection is enabled.

cBladeStatsTable  OBJECT-TYPE
    SYNTAX      SEQUENCE OF CBladeStatsEntry
    MAX-ACCESS  not-accessible
    STATUS      current
    DESCRIPTION
            "A list of cBlade Monitor entries containing runtime statistics
            for cBlades."

        ::=     { cBlades 2 }


cBladeStatsEntry OBJECT-TYPE
    SYNTAX      CBladeStatsEntry
    MAX-ACCESS  not-accessible
    STATUS      current
    DESCRIPTION
            "A cBlade Monitor entry contains runtime statistics for
            cBlades."

    INDEX       { bladeFrameIndex, cBladeIndex }
        ::=     { cBladeStatsTable 1 }


CBladeStatsEntry ::=
    SEQUENCE {
        cBladeStatsUpTime
            TimeTicks,
        cBladeStatsLoadAvg1
            Gauge32,
        cBladeStatsLoadAvg5
            Gauge32,
        cBladeStatsLoadAvg15
            Gauge32,
        cBladeStatsCpuUser
            Counter32,
        cBladeStatsCpuSystem
            Counter32,
        cBladeStatsCpuIdle
            Counter32,
        cBladeStatsLoadScale
            Gauge32,
        cBladeStatsNumProcs
            Gauge32,
        cBladeStatsLastPid
            Integer32,
        cBladeStatsContextSwitch
            Counter32,
        cBladeStatsInterrupt
            Counter32,
        cBladeStatsMemTotal
            Gauge32,
        cBladeStatsMemFree
            Gauge32,
        cBladeStatsSwapTotal
            Gauge32,
        cBladeStatsSwapFree
            Gauge32,
        cBladeStatsPageIn
            Counter32,
        cBladeStatsPageOut
            Counter32,
        cBladeStatsSwapIn
            Counter32,
        cBladeStatsSwapOut
            Counter32,
        cBladeStatsDiskReads
            Counter32,
        cBladeStatsDiskWrites
            Counter32,
        cBladeStatsDiskBlkReads
            Counter32,
        cBladeStatsDiskBlkWrites
            Counter32,
        cBladeStatsCpuUserNice
            Counter32,
        cBladeStatsHeapTotal
            Gauge32,
        cBladeStatsHeapUsed
            Gauge32,
        cBladeStatsHeapCommitted
            Gauge32,
        cBladeStatsNonHeapTotal
            Gauge32,
        cBladeStatsNonHeapUsed
            Gauge32,
        cBladeStatsNonHeapCommitted
            Gauge32,
	cBladeStatsFilesTotal
            Gauge32,
	cBladeStatsFilesUsed
            Gauge32,
	cBladeStatsSocketsUsed
            Gauge32
    }

cBladeStatsUpTime OBJECT-TYPE
    SYNTAX      TimeTicks
    MAX-ACCESS  read-only
    STATUS      current
    DESCRIPTION
            "The uptime in 1/100ths of a second for this cBlade."

        ::=     { cBladeStatsEntry 1 }


cBladeStatsLoadAvg1 OBJECT-TYPE
    SYNTAX      Gauge32
    MAX-ACCESS  read-only
    STATUS      current
    DESCRIPTION
            "100 * the average number of jobs in the run queue over the
            previous minute."

        ::=     { cBladeStatsEntry 2 }


cBladeStatsLoadAvg5 OBJECT-TYPE
    SYNTAX      Gauge32
    MAX-ACCESS  read-only
    STATUS      current
    DESCRIPTION
            "100 * the average number of jobs in the run queue over the
            previous five minutes."

        ::=     { cBladeStatsEntry 3 }


cBladeStatsLoadAvg15 OBJECT-TYPE
    SYNTAX      Gauge32
    MAX-ACCESS  read-only
    STATUS      current
    DESCRIPTION
            "100 * the average number of jobs in the run queue over the
            previous fifteen minutes."

        ::=     { cBladeStatsEntry 4 }


cBladeStatsCpuUser OBJECT-TYPE
    SYNTAX      Counter32
    MAX-ACCESS  read-only
    STATUS      current
    DESCRIPTION
            "The number of (1/100)ths of a second that the cBlade spent in
            user mode since boot."

        ::=     { cBladeStatsEntry 5 }


cBladeStatsCpuSystem OBJECT-TYPE
    SYNTAX      Counter32
    MAX-ACCESS  read-only
    STATUS      current
    DESCRIPTION
            "The number of (1/100)ths of a second that the cBlade spent in
            system mode since boot."

        ::=     { cBladeStatsEntry 6 }


cBladeStatsCpuIdle OBJECT-TYPE
    SYNTAX      Counter32
    MAX-ACCESS  read-only
    STATUS      current
    DESCRIPTION
            "The number of (1/100)ths of a second that the cBlade spent in
            idle mode since boot."

        ::=     { cBladeStatsEntry 7 }


cBladeStatsLoadScale OBJECT-TYPE
    SYNTAX      Gauge32
    MAX-ACCESS  read-only
    STATUS      current
    DESCRIPTION
            "The current load scale."

        ::=     { cBladeStatsEntry 8 }


cBladeStatsNumProcs OBJECT-TYPE
    SYNTAX      Gauge32
    MAX-ACCESS  read-only
    STATUS      current
    DESCRIPTION
            "The current number of processes running on the cBlade."

        ::=     { cBladeStatsEntry 9 }


cBladeStatsLastPid OBJECT-TYPE
    SYNTAX      Integer32
    MAX-ACCESS  read-only
    STATUS      current
    DESCRIPTION
            "The highest allocated process ID on the cBlade."

        ::=     { cBladeStatsEntry 10 }


cBladeStatsContextSwitch OBJECT-TYPE
    SYNTAX      Counter32
    MAX-ACCESS  read-only
    STATUS      current
    DESCRIPTION
            "The number of context switches undergone by this cBlade since
            boot."

        ::=     { cBladeStatsEntry 11 }


cBladeStatsInterrupt OBJECT-TYPE
    SYNTAX      Counter32
    MAX-ACCESS  read-only
    STATUS      current
    DESCRIPTION
            "The number of interrupts encountered by this cBlade since
            boot."

        ::=     { cBladeStatsEntry 12 }


cBladeStatsMemTotal OBJECT-TYPE
    SYNTAX      Gauge32
    MAX-ACCESS  read-only
    STATUS      current
    DESCRIPTION
            "The total amount of physical RAM in kB for this cBlade."

        ::=     { cBladeStatsEntry 13 }


cBladeStatsMemFree OBJECT-TYPE
    SYNTAX      Gauge32
    MAX-ACCESS  read-only
    STATUS      current
    DESCRIPTION
            "The amount of free physcial RAM in kB for this cBlade."

        ::=     { cBladeStatsEntry 14 }


cBladeStatsSwapTotal OBJECT-TYPE
    SYNTAX      Gauge32
    MAX-ACCESS  read-only
    STATUS      current
    DESCRIPTION
            "The total amount of configured swap memory in kB for this
            cBlade."

        ::=     { cBladeStatsEntry 15 }


cBladeStatsSwapFree OBJECT-TYPE
    SYNTAX      Gauge32
    MAX-ACCESS  read-only
    STATUS      current
    DESCRIPTION
            "The amount of free swap memory in kB for this cBlade."

        ::=     { cBladeStatsEntry 16 }


cBladeStatsPageIn OBJECT-TYPE
    SYNTAX      Counter32
    MAX-ACCESS  read-only
    STATUS      current
    DESCRIPTION
            "The number of pages paged in since boot."

        ::=     { cBladeStatsEntry 17 }


cBladeStatsPageOut OBJECT-TYPE
    SYNTAX      Counter32
    MAX-ACCESS  read-only
    STATUS      current
    DESCRIPTION
            "The number of pages paged out since boot."

        ::=     { cBladeStatsEntry 18 }


cBladeStatsSwapIn OBJECT-TYPE
    SYNTAX      Counter32
    MAX-ACCESS  read-only
    STATUS      current
    DESCRIPTION
            "The number of swap pages paged in since boot."

        ::=     { cBladeStatsEntry 19 }


cBladeStatsSwapOut OBJECT-TYPE
    SYNTAX      Counter32
    MAX-ACCESS  read-only
    STATUS      current
    DESCRIPTION
            "The number of swap pages paged out since boot."

        ::=     { cBladeStatsEntry 20 }


cBladeStatsDiskReads OBJECT-TYPE
    SYNTAX      Counter32
    MAX-ACCESS  read-only
    STATUS      current
    DESCRIPTION
            "The number of disk reads since boot."

        ::=     { cBladeStatsEntry 21 }


cBladeStatsDiskWrites OBJECT-TYPE
    SYNTAX      Counter32
    MAX-ACCESS  read-only
    STATUS      current
    DESCRIPTION
            "The number of disk writes since boot."

        ::=     { cBladeStatsEntry 22 }


cBladeStatsDiskBlkReads OBJECT-TYPE
    SYNTAX      Counter32
    MAX-ACCESS  read-only
    STATUS      current
    DESCRIPTION
            "The number of 1 kB blocks read from disk since boot."

        ::=     { cBladeStatsEntry 23 }


cBladeStatsDiskBlkWrites OBJECT-TYPE
    SYNTAX      Counter32
    MAX-ACCESS  read-only
    STATUS      current
    DESCRIPTION
            "The number of of 1 kB blocks written to disk since boot."

        ::=     { cBladeStatsEntry 24 }


cBladeStatsCpuUserNice OBJECT-TYPE
    SYNTAX      Counter32
    MAX-ACCESS  read-only
    STATUS      current
    DESCRIPTION
            "The number of (1/100)ths of a second that the cBlade spent in
            user nice mode since boot."

        ::=     { cBladeStatsEntry 25 }

cBladeStatsHeapTotal OBJECT-TYPE
    SYNTAX      Gauge32
    MAX-ACCESS  read-only
    STATUS      current
    DESCRIPTION
            "The total amount of Java Heap Memory in kB for this cBlade."

        ::=     { cBladeStatsEntry 26 }

cBladeStatsHeapUsed OBJECT-TYPE
    SYNTAX      Gauge32
    MAX-ACCESS  read-only
    STATUS      current
    DESCRIPTION
            "The amount of used Java Heap Memory in kB for this cBlade."

        ::=     { cBladeStatsEntry 27 }

cBladeStatsHeapCommitted OBJECT-TYPE
    SYNTAX      Gauge32
    MAX-ACCESS  read-only
    STATUS      current
    DESCRIPTION
            "The amount of committed Java Heap Memory in kB for this cBlade."

        ::=     { cBladeStatsEntry 28 }

cBladeStatsNonHeapTotal OBJECT-TYPE
    SYNTAX      Gauge32
    MAX-ACCESS  read-only
    STATUS      current
    DESCRIPTION
            "The total amount of Java Non-Heap Memory in kB for this cBlade."

        ::=     { cBladeStatsEntry 29 }


cBladeStatsNonHeapUsed OBJECT-TYPE
    SYNTAX      Gauge32
    MAX-ACCESS  read-only
    STATUS      current
    DESCRIPTION
            "The amount of used Java Non-Heap Memory in kB for this cBlade."

        ::=     { cBladeStatsEntry 30 }

cBladeStatsNonHeapCommitted OBJECT-TYPE
    SYNTAX      Gauge32
    MAX-ACCESS  read-only
    STATUS      current
    DESCRIPTION
            "The amount of committed Java Non-Heap Memory in kB for this cBlade."

        ::=     { cBladeStatsEntry 31 }

cBladeStatsFilesTotal OBJECT-TYPE
    SYNTAX      Gauge32
    MAX-ACCESS  read-only
    STATUS      current
    DESCRIPTION
            "The maximum number of PAN Manager file descriptors for this cBlade."

        ::=     { cBladeStatsEntry 32 }

cBladeStatsFilesUsed OBJECT-TYPE
    SYNTAX      Gauge32
    MAX-ACCESS  read-only
    STATUS      current
    DESCRIPTION
            "The number of file descriptors in use by PAN Manager for this cBlade."

        ::=     { cBladeStatsEntry 33 }

cBladeStatsSocketsUsed OBJECT-TYPE
    SYNTAX      Gauge32
    MAX-ACCESS  read-only
    STATUS      current
    DESCRIPTION
            "The number of socket descriptors in use by PAN Manager for this cBlade."

        ::=     { cBladeStatsEntry 34 }

-- cBlade CPU Table
-- Contains information about each CPU on each cBlade

cBladeCpuTable   OBJECT-TYPE
    SYNTAX      SEQUENCE OF CBladeCpuEntry
    MAX-ACCESS  not-accessible
    STATUS      current
    DESCRIPTION
            "A list of CPU statisitcs for each CPU on each cBlade."

        ::=     { cBlades 3 }


cBladeCpuEntry OBJECT-TYPE
    SYNTAX      CBladeCpuEntry
    MAX-ACCESS  not-accessible
    STATUS      current
    DESCRIPTION
            "Statistics for each CPU on the cBlade."

    INDEX       { bladeFrameIndex, cBladeIndex, cBladeCpuIndex }
        ::=     { cBladeCpuTable 1 }


CBladeCpuEntry ::=
    SEQUENCE {
        cBladeCpuIndex
            Integer32,
        cBladeCpuCBladeIndex
            Integer32,
        cBladeCpuLPanIndex
            Integer32,
        cBladeCpuModelName
            DisplayString,
        cBladeCpuModel
            Integer32,
        cBladeCpuFamily
            Integer32,
        cBladeCpuVendorId
            DisplayString,
        cBladeCpuMhz
            Integer32,
        cBladeCpuCacheSize
            Integer32,
        cBladeCpuName
            DisplayString,
        cBladeCpuUser
            Counter32,
        cBladeCpuUserNice
            Counter32,
        cBladeCpuSystem
            Counter32,
        cBladeCpuIdle
            Counter32
    }


cBladeCpuIndex OBJECT-TYPE
    SYNTAX      Integer32 (1..2147483647)
    MAX-ACCESS  read-only
    STATUS      current
    DESCRIPTION
            "An integer uniquely identifying this CPU within the cBlade."

        ::=     { cBladeCpuEntry 1 }


cBladeCpuCBladeIndex OBJECT-TYPE
    SYNTAX      Integer32 (1..2147483647)
    MAX-ACCESS  read-only
    STATUS      current
    DESCRIPTION
            "An integer value identifying the cBladeIndex value of the
            cBlade that hosts this CPU."

        ::=     { cBladeCpuEntry 2 }


cBladeCpuLPanIndex OBJECT-TYPE
    SYNTAX      Integer32 (1..2147483647)
    MAX-ACCESS  read-only
    STATUS      current
    DESCRIPTION
            "This object is deprecated."

        ::=     { cBladeCpuEntry 3 }


cBladeCpuModelName OBJECT-TYPE
    SYNTAX      DisplayString
    MAX-ACCESS  read-only
    STATUS      current
    DESCRIPTION
            "A textual string representing the CPU model."

        ::=     { cBladeCpuEntry 4 }


cBladeCpuModel OBJECT-TYPE
    SYNTAX      Integer32
    MAX-ACCESS  read-only
    STATUS      current
    DESCRIPTION
            "An integer value representing the CPU model."

        ::=     { cBladeCpuEntry 5 }


cBladeCpuFamily OBJECT-TYPE
    SYNTAX      Integer32
    MAX-ACCESS  read-only
    STATUS      current
    DESCRIPTION
            "An integer value representing the CPU family."

        ::=     { cBladeCpuEntry 6 }


cBladeCpuVendorId OBJECT-TYPE
    SYNTAX      DisplayString
    MAX-ACCESS  read-only
    STATUS      current
    DESCRIPTION
            "A textual string representing the CPU vendor."

        ::=     { cBladeCpuEntry 7 }


cBladeCpuMhz OBJECT-TYPE
    SYNTAX      Integer32
    MAX-ACCESS  read-only
    STATUS      current
    DESCRIPTION
            "The speed of the CPU in Mhz."

        ::=     { cBladeCpuEntry 8 }


cBladeCpuCacheSize OBJECT-TYPE
    SYNTAX      Integer32
    MAX-ACCESS  read-only
    STATUS      current
    DESCRIPTION
            "The cache size of the CPU in MB."

        ::=     { cBladeCpuEntry 9 }


cBladeCpuName OBJECT-TYPE
    SYNTAX      DisplayString
    MAX-ACCESS  read-only
    STATUS      current
    DESCRIPTION
            "A textual string uniquely identifying this CPU."

        ::=     { cBladeCpuEntry 10 }


cBladeCpuUser OBJECT-TYPE
    SYNTAX      Counter32
    MAX-ACCESS  read-only
    STATUS      current
    DESCRIPTION
            "The number of (1/100)ths of a second that this CPU spent in
            user mode since boot."

        ::=     { cBladeCpuEntry 11 }


cBladeCpuUserNice OBJECT-TYPE
    SYNTAX      Counter32
    MAX-ACCESS  read-only
    STATUS      current
    DESCRIPTION
            "The number of (1/100)ths of a second that this CPU spent in
            user nice mode since boot."

        ::=     { cBladeCpuEntry 12 }


cBladeCpuSystem OBJECT-TYPE
    SYNTAX      Counter32
    MAX-ACCESS  read-only
    STATUS      current
    DESCRIPTION
            "The number of (1/100)ths of a second that this CPU spent in
            system mode since boot."

        ::=     { cBladeCpuEntry 13 }


cBladeCpuIdle OBJECT-TYPE
    SYNTAX      Counter32
    MAX-ACCESS  read-only
    STATUS      current
    DESCRIPTION
            "The number of (1/100)ths of a second that this CPU spent in
            idle mode since boot."

        ::=     { cBladeCpuEntry 14 }



-- cBlade Disk Table
-- Contains information about each disk on the cBlade.

cBladeDiskTable OBJECT-TYPE

    SYNTAX      SEQUENCE OF CBladeDiskEntry
    MAX-ACCESS  not-accessible
    STATUS      current
    DESCRIPTION
            "A list of disk statisitcs for each disk on the
            cBlade."

        ::=     { cBlades 4 }


cBladeDiskEntry OBJECT-TYPE
    SYNTAX      CBladeDiskEntry
    MAX-ACCESS  not-accessible
    STATUS      current
    DESCRIPTION
            "Disk statisitcs for each disk on the cBlade."

    INDEX       { bladeFrameIndex, cBladeIndex,
                  IMPLIED cBladeDiskNameOctets }
        ::=     { cBladeDiskTable 1 }

CBladeDiskEntry ::=
    SEQUENCE {
        cBladeDiskNameOctets
            OCTET STRING,
        cBladeDiskCBladeIndex
            Integer32,
        cBladeDiskBladeFrameIndex
            Integer32,
        cBladeDiskName
            DisplayString,
        cBladeDiskBlocks
            Gauge32,
        cBladeDiskMajor
            Integer32,
        cBladeDiskMinor
            Integer32
    }

cBladeDiskNameOctets OBJECT-TYPE
    SYNTAX      OCTET STRING (SIZE(0..32))
    MAX-ACCESS  read-only
    STATUS      current
    DESCRIPTION
            "An octet string representing the device special file name
            representing this disk."

        ::=     { cBladeDiskEntry 1 }


cBladeDiskCBladeIndex OBJECT-TYPE
    SYNTAX      Integer32
    MAX-ACCESS  read-only
    STATUS      current
    DESCRIPTION
            "An integer value identifying the cBladeIndex value of the
            cBlade that utilizes this disk."

        ::=     { cBladeDiskEntry 2 }


cBladeDiskBladeFrameIndex OBJECT-TYPE
    SYNTAX      Integer32
    MAX-ACCESS  read-only
    STATUS      current
    DESCRIPTION
            "An integer value indentifying the bladeFrameIndex value of the
            BladeFrame that hosts this disk."

        ::=     { cBladeDiskEntry 3 }

cBladeDiskName OBJECT-TYPE
    SYNTAX      DisplayString
    MAX-ACCESS  read-only
    STATUS      current
    DESCRIPTION
            "The human readable device special file name representing this
            disk."

        ::=     { cBladeDiskEntry 4 }


cBladeDiskBlocks OBJECT-TYPE
    SYNTAX      Gauge32
    MAX-ACCESS  read-only
    STATUS      current
    DESCRIPTION
            "The size of this disk in 1kB blocks"

        ::=     { cBladeDiskEntry 5 }


cBladeDiskMajor OBJECT-TYPE
    SYNTAX      Integer32
    MAX-ACCESS  read-only
    STATUS      current
    DESCRIPTION
            "The major ID of this disk."

        ::=     { cBladeDiskEntry 6 }


cBladeDiskMinor OBJECT-TYPE
    SYNTAX      Integer32
    MAX-ACCESS  read-only
    STATUS      current
    DESCRIPTION
            "The minor ID of this disk."

        ::=     { cBladeDiskEntry 7 }


-- cBlade Partition Table
-- Contains information about each disk partition on the cBlade.



cBladePartitionTable   OBJECT-TYPE
    SYNTAX      SEQUENCE OF CBladePartitionEntry
    MAX-ACCESS  not-accessible
    STATUS      current
    DESCRIPTION
            "A list of partition statisitcs for each partition on the
            cBlade."

        ::=     { cBlades 5 }


cBladePartitionEntry OBJECT-TYPE
    SYNTAX      CBladePartitionEntry
    MAX-ACCESS  not-accessible
    STATUS      current
    DESCRIPTION
            "Partition statisitcs for each partition on the cBlade."
    INDEX       { bladeFrameIndex, cBladeIndex,
                  IMPLIED cBladePartitionNameOctets }
        ::=     { cBladePartitionTable 1 }


CBladePartitionEntry ::=
    SEQUENCE {
        cBladePartitionNameOctets
            OCTET STRING,
        cBladePartitionCBladeIndex
            Integer32,
        cBladePartitionLPanIndex
            Integer32,
        cBladePartitionName
            DisplayString,
        cBladePartitionBlocks
            Gauge32,
        cBladePartitionMajor
            Integer32,
        cBladePartitionMinor
            Integer32,
        cBladePartitionFSBlocks
            Gauge32,
        cBladePartitionFSUsedBlocks
            Gauge32,
        cBladePartitionFSAvailableBlocks
            Gauge32,
        cBladePartitionFSUtil
            Gauge32
    }


cBladePartitionNameOctets OBJECT-TYPE
    SYNTAX      OCTET STRING (SIZE(0..63))
    MAX-ACCESS  read-only
    STATUS      current
    DESCRIPTION
            "An octet string representing the device special file name
            representing this disk."

        ::=     { cBladePartitionEntry 1 }


cBladePartitionCBladeIndex OBJECT-TYPE
    SYNTAX      Integer32
    MAX-ACCESS  read-only
    STATUS      current
    DESCRIPTION
            "An integer value identifying the cBladeIndex value of the
            cBlade that utilizes this disk partition."

        ::=     { cBladePartitionEntry 2 }


cBladePartitionLPanIndex OBJECT-TYPE
    SYNTAX      Integer32
    MAX-ACCESS  read-only
    STATUS      current
    DESCRIPTION
            "This object is deprecated."

        ::=     { cBladePartitionEntry 3 }


cBladePartitionName OBJECT-TYPE
    SYNTAX      DisplayString (SIZE(0..63))
    MAX-ACCESS  read-only
    STATUS      current
    DESCRIPTION
            "A textual string identifying the device file that represents
            this partition."

        ::=     { cBladePartitionEntry 4 }


cBladePartitionBlocks OBJECT-TYPE
    SYNTAX      Gauge32
    MAX-ACCESS  read-only
    STATUS      current
    DESCRIPTION
            "The size of this partition in 1kB blocks"

        ::=     { cBladePartitionEntry 5 }


cBladePartitionMajor OBJECT-TYPE
    SYNTAX      Integer32
    MAX-ACCESS  read-only
    STATUS      current
    DESCRIPTION
            "The major ID of this partition."

        ::=     { cBladePartitionEntry 6 }


cBladePartitionMinor OBJECT-TYPE
    SYNTAX      Integer32
    MAX-ACCESS  read-only
    STATUS      current
    DESCRIPTION
            "The minor ID of this partition."

        ::=     { cBladePartitionEntry 7 }



cBladePartitionFSBlocks OBJECT-TYPE
    SYNTAX      Gauge32
    MAX-ACCESS  read-only
    STATUS      current
    DESCRIPTION
            "If the partition contains a mounted filesystem, filesystem size
            in 1k blocks, othewise 0"

        ::=     { cBladePartitionEntry 8 }


cBladePartitionFSUsedBlocks OBJECT-TYPE
    SYNTAX      Gauge32
    MAX-ACCESS  read-only
    STATUS      current
    DESCRIPTION
            "If the partition contains a mounted filesystem, the number of
            used 1k blocks, otherwise 0"

        ::=     { cBladePartitionEntry 9 }


cBladePartitionFSAvailableBlocks OBJECT-TYPE
    SYNTAX      Gauge32
    MAX-ACCESS  read-only
    STATUS      current
    DESCRIPTION
            "If the partition contains a mounted filesystem, the number of
            available 1k blocks, otherwise 0"

        ::=     { cBladePartitionEntry 10 }


cBladePartitionFSUtil OBJECT-TYPE
    SYNTAX      Gauge32
    MAX-ACCESS  read-only
    STATUS      current
    DESCRIPTION
            "If the partition contains a mounted filesystem, the number of
            available 1k blocks, otherwise 0"

        ::=     { cBladePartitionEntry 11 }



-- cBlade Virtual Ethernet table
-- Contains information about each network interface on the cBlade.


InterfaceOperStatus ::= TEXTUAL-CONVENTION
    STATUS      current
    DESCRIPTION
            "Describes network interface operational status."
    SYNTAX INTEGER {
        up(1),        -- ready to pass packets
        down(2),
        testing(3),   -- in some test mode
        unknown(4),   -- status can not be determined
                      -- for some reason.
        dormant(5),
        notPresent(6),    -- some component is missing
        lowerLayerDown(7) -- down due to state of
                          -- lower-layer interface(s)
    }

EthRethStatus ::= TEXTUAL-CONVENTION
    STATUS      current
    DESCRIPTION
            "Describes the state of the eth with respect to REth
            membership."
    SYNTAX INTEGER {
        active(1),      -- actively communcating
        standby(2),     -- waiting to take over in case of failure
        failed(3),      -- link or ping failure detected
        unconfigured(4),-- not part of a Reth
        unknown(999)
    }

cBladeEthTable   OBJECT-TYPE
    SYNTAX      SEQUENCE OF CBladeEthEntry
    MAX-ACCESS  not-accessible
    STATUS      current
    DESCRIPTION
            "physical Network Interface Cards (NICs) on a BladeFrame's
                   cBlades (cBlades).

            each cBlade has the following three NICs:

                   o      One internal management port
                   o      One 2-port 10/100 Ethernet
                   o      One Gigabit Ethernet

                   The NICs are named as follows:

                   o      cBladeEth0 is the internal management port
                   o      cBladeEth1 is one of the 10/100 ports
                   o      cBladeEth2 is the other 10/100 port
                   o      cBladeEth3 is the Gigabit Ethernet"


        ::=     { cBlades 6 }


cBladeEthEntry OBJECT-TYPE
    SYNTAX      CBladeEthEntry
    MAX-ACCESS  not-accessible
    STATUS      current
    DESCRIPTION
            "Information specific to each cBlade Eth in the PAN."

    INDEX       { bladeFrameIndex, cBladeIndex, cBladeEthIndex }
        ::=     { cBladeEthTable 1 }

CBladeEthEntry ::=
    SEQUENCE {
        cBladeEthIndex
            Integer32,
        cBladeEthCBladeIndex
            Integer32,
        cBladeEthBladeFrameIndex
            Integer32,
        cBladeEthName
            DisplayString,
        cBladeEthFullName
            DisplayString,
        cBladeEthHwMACAddressOctets
            PhysAddress,
        cBladeEthHwMACAddressString
            DisplayString,
        cBladeEthSwMACAddressOctets
            PhysAddress,
        cBladeEthSwMACAddressString
            DisplayString,
        cBladeEthNICType
            DisplayString,
        cBladeEthFiltered
            TruthValue,
        cBladeEthUplinkName
            DisplayString,
        cBladeEthUplinkPort
            Integer32,
        cBladeEthLinkState
            InterfaceOperStatus,
        cBladeEthRethStatus
            EthRethStatus
    }

cBladeEthIndex OBJECT-TYPE
    SYNTAX      Integer32 (1..2147483647)
    MAX-ACCESS  read-only
    STATUS      current
    DESCRIPTION
            "An integer value uniquely identifying the cBladeEth within the
            cBlade."

        ::=     { cBladeEthEntry 1 }


cBladeEthCBladeIndex OBJECT-TYPE
    SYNTAX      Integer32 (1..2147483647)
    MAX-ACCESS  read-only
    STATUS      current
    DESCRIPTION
            "An integer value identifying the cBladeIndex value of the
            cBlade that hosts this Eth."

        ::=     { cBladeEthEntry 2 }


cBladeEthBladeFrameIndex OBJECT-TYPE
    SYNTAX      Integer32 (1..2147483647)
    MAX-ACCESS  read-only
    STATUS      current
    DESCRIPTION
            "An integer value identifying the bladeFrameIndex value of the
            BladeFrame that hosts this Eth."

        ::=     { cBladeEthEntry 3 }


cBladeEthName OBJECT-TYPE
    SYNTAX      DisplayString
    MAX-ACCESS  read-only
    STATUS      current
    DESCRIPTION
            "A human readable string uniquely identifying the cBlade Eth."

        ::=     { cBladeEthEntry 4 }


cBladeEthFullName OBJECT-TYPE
    SYNTAX      DisplayString
    MAX-ACCESS  read-only
    STATUS      current
    DESCRIPTION
            "A human readable string uniquely identifying the cBlade Eth,
            including the host cBlade and BladeFrame."

        ::=     { cBladeEthEntry 5 }


cBladeEthHwMACAddressOctets OBJECT-TYPE
    SYNTAX      PhysAddress
    MAX-ACCESS  read-only
    STATUS      current
    DESCRIPTION
            "An encoding of the cBlade Eth hardware MAC address."

        ::=     { cBladeEthEntry 6 }


cBladeEthHwMACAddressString OBJECT-TYPE
    SYNTAX      DisplayString
    MAX-ACCESS  read-only
    STATUS      current
    DESCRIPTION
            "A human readable string representing the cBlade Eth hardware
            MAC address in the form: '6E:4A:1F:00:01:06'."

        ::=     { cBladeEthEntry 7 }


cBladeEthSwMACAddressOctets OBJECT-TYPE
    SYNTAX      PhysAddress
    MAX-ACCESS  read-only
    STATUS      current
    DESCRIPTION
            "This object is deprecated.  As of release 5.0, software MA
            addresses are not supported on cBlade eths."


        ::=     { cBladeEthEntry 8 }


cBladeEthSwMACAddressString OBJECT-TYPE
    SYNTAX      DisplayString
    MAX-ACCESS  read-only
    STATUS      current
    DESCRIPTION
            "This object is deprecated.  As of release 5.0, software MA
            addresses are not supported on cBlade eths."

        ::=     { cBladeEthEntry 9 }


cBladeEthNICType OBJECT-TYPE
    SYNTAX      DisplayString
    MAX-ACCESS  read-only
    STATUS      current
    DESCRIPTION
            "Specifies the cBlade ETH NIC type, such as e100 or e1000."

        ::=     { cBladeEthEntry 10 }


cBladeEthFiltered OBJECT-TYPE
    SYNTAX      TruthValue
    MAX-ACCESS  read-only
    STATUS      current
    DESCRIPTION
            "This object is deprecated.  As of release 5.0, filtered mode
            is not supported on cBlade eths."

        ::=     { cBladeEthEntry 11 }


cBladeEthUplinkName OBJECT-TYPE
    SYNTAX      DisplayString
    MAX-ACCESS  read-only
    STATUS      current
    DESCRIPTION
            "A human readable string that a PAN or BladeFrame Administrator
            assigns to describe the uplink port."

        ::=     { cBladeEthEntry 12 }


cBladeEthUplinkPort OBJECT-TYPE
    SYNTAX      Integer32
    MAX-ACCESS  read-only
    STATUS      current
    DESCRIPTION
            "An integer value that a PAN or BladeFrame Administrator assigns
            to identify the uplink port."

        ::=     { cBladeEthEntry 13 }


cBladeEthLinkState OBJECT-TYPE
    SYNTAX      InterfaceOperStatus
    MAX-ACCESS  read-only
    STATUS      current
    DESCRIPTION
            "The Link State of the Eth."

        ::=     { cBladeEthEntry 14 }


cBladeEthRethStatus OBJECT-TYPE
    SYNTAX      EthRethStatus
    MAX-ACCESS  read-only
    STATUS      current
    DESCRIPTION
            "The State of the Eth with respect to REth membership."

        ::=     { cBladeEthEntry 15 }


-- table of VLANs for each cBlade Eth

cBladeEthVLANTable   OBJECT-TYPE
    SYNTAX      SEQUENCE OF CBladeEthVLANEntry
    MAX-ACCESS  not-accessible
    STATUS      current
    DESCRIPTION
            "A list of VLAN IDs and descriptions associated with each Eth."

        ::=     { cBlades 7 }


cBladeEthVLANEntry OBJECT-TYPE
    SYNTAX      CBladeEthVLANEntry
    MAX-ACCESS  not-accessible
    STATUS      current
    DESCRIPTION
            "Information specific to each VLAN for cBlade cBladeEths."

    INDEX       { bladeFrameIndex, cBladeIndex, cBladeEthIndex, cBladeEthVLANId }
        ::=     { cBladeEthVLANTable 1 }

CBladeEthVLANEntry ::=
    SEQUENCE {
        cBladeEthVLANId
            Integer32,
        cBladeEthVLANEthIndex
            Integer32,
        cBladeEthVLANcBladeIndex
            Integer32,
        cBladeEthVLANBladeFrameIndex
            Integer32,
        cBladeEthVLANEthName
            DisplayString,
        cBladeEthVLANName
            DisplayString
    }


cBladeEthVLANId OBJECT-TYPE
    SYNTAX      Integer32 (1..4094)
    MAX-ACCESS  read-only
    STATUS      current
    DESCRIPTION
            "specifies a VLAN ID assigned to the uplink port on the physical
            network component connected to the cBlade NIC"

        ::=     { cBladeEthVLANEntry 1 }


cBladeEthVLANEthIndex OBJECT-TYPE
    SYNTAX      Integer32
    MAX-ACCESS  read-only
    STATUS      current
    DESCRIPTION
            "An integer value identifying the cBladeEthIndex value of the
            cBlade Eth that hosts this Eth VLAN."

        ::=     { cBladeEthVLANEntry 2 }


cBladeEthVLANcBladeIndex OBJECT-TYPE
    SYNTAX      Integer32
    MAX-ACCESS  read-only
    STATUS      current
    DESCRIPTION
            "An integer value identifying the cBladeIndex value of the
            cBlade that hosts this Eth VLAN."

        ::=     { cBladeEthVLANEntry 3 }


cBladeEthVLANBladeFrameIndex OBJECT-TYPE
    SYNTAX      Integer32
    MAX-ACCESS  read-only
    STATUS      current
    DESCRIPTION
            "An integer value identifying the bladeFrameIndex value of the
            BladeFrame that hosts this Eth VLAN."

        ::=     { cBladeEthVLANEntry 4 }


cBladeEthVLANEthName OBJECT-TYPE
    SYNTAX      DisplayString
    MAX-ACCESS  read-only
    STATUS      current
    DESCRIPTION
            "The full name of the ethernet interface associated with this VLAN."

        ::=     { cBladeEthVLANEntry 5 }


cBladeEthVLANName OBJECT-TYPE
    SYNTAX      DisplayString
    MAX-ACCESS  read-only
    STATUS      current
    DESCRIPTION
            "A human readable string that a PAN or BladeFrame Administrator
            assigns to the VLAN."

        ::=     { cBladeEthVLANEntry 6 }


-- table of cBlade VEth Stats

cBladeVEthStatsTable   OBJECT-TYPE
    SYNTAX      SEQUENCE OF CBladeVEthStatsEntry
    MAX-ACCESS  not-accessible
    STATUS      current
    DESCRIPTION
            "A list of interface statisitcs for each virtual interface in the
            cBlade.

            Since REths remove their composit Eths from the Linux network
            stack, physical Eth statistics are not avaialble.  This table
            exports statistics for cBlade VEths, including the internal and
            external management network VEths."

        ::=     { cBlades 8 }

cBladeVEthStatsEntry OBJECT-TYPE
    SYNTAX      CBladeVEthStatsEntry
    MAX-ACCESS  not-accessible
    STATUS      current
    DESCRIPTION
            "VEthStats statisitcs for each virtual interface in the cBlade."

    INDEX       { bladeFrameIndex, cBladeIndex, cBladeVEthIndex }
        ::=     { cBladeVEthStatsTable 1 }


CBladeVEthStatsEntry ::=
    SEQUENCE {
        cBladeVEthIndex
            Integer32,
        cBladeVEthCBladeIndex
            Integer32,
        cBladeVEthBladeFrameIndex
            Integer32,
        cBladeVEthName
            DisplayString,
        cBladeVEthStatsInBytes
            Counter32,
        cBladeVEthStatsInPackets
            Counter32,
        cBladeVEthStatsInErrs
            Counter32,
        cBladeVEthStatsInDrops
            Counter32,
        cBladeVEthStatsInOverrun
            Counter32,
        cBladeVEthStatsInMulticast
            Counter32,
        cBladeVEthStatsOutBytes
            Counter32,
        cBladeVEthStatsOutPackets
            Counter32,
        cBladeVEthStatsOutErrs
            Counter32,
        cBladeVEthStatsOutDrops
            Counter32,
        cBladeVEthStatsOutOverrun
            Counter32,
        cBladeVEthStatsOutCollisions
            Counter32,
        cBladeVEthStatsOutCarrierDctFail
            Counter32,
        cBladeVEthStatsOutCompressed
            Counter32,
        cBladeVEthStatsOperStatus
            InterfaceOperStatus
    }


cBladeVEthIndex OBJECT-TYPE
    SYNTAX      Integer32 (1..2147483647)
    MAX-ACCESS  read-only
    STATUS      current
    DESCRIPTION
            "An integer value uniquely identifying the VEth within the cBlade."

        ::=     { cBladeVEthStatsEntry 1 }


cBladeVEthCBladeIndex OBJECT-TYPE
    SYNTAX      Integer32
    MAX-ACCESS  read-only
    STATUS      current
    DESCRIPTION
           "The cBladeIndex value of the cBlade hosting this VEth."

        ::=     { cBladeVEthStatsEntry 2 }


cBladeVEthBladeFrameIndex OBJECT-TYPE
    SYNTAX      Integer32
    MAX-ACCESS  read-only
    STATUS      current
    DESCRIPTION
           "The bladeFrameIndex value of the BladeFrame hosting this VEth."

        ::=     { cBladeVEthStatsEntry 3 }


cBladeVEthName OBJECT-TYPE
    SYNTAX      DisplayString
    MAX-ACCESS  read-only
    STATUS      current
    DESCRIPTION
            "A string uniquely identifying this VEth on this cBlade."

        ::=     { cBladeVEthStatsEntry 4 }


cBladeVEthStatsInBytes OBJECT-TYPE
    SYNTAX      Counter32
    MAX-ACCESS  read-only
    STATUS      current
    DESCRIPTION
            "The number of bytes received on this interface since interface
            reset"

        ::=     { cBladeVEthStatsEntry 5 }


cBladeVEthStatsInPackets OBJECT-TYPE
    SYNTAX      Counter32
    MAX-ACCESS  read-only
    STATUS      current
    DESCRIPTION
            "The number of packets received on this interface since interface
            reset"

        ::=     { cBladeVEthStatsEntry 6 }


cBladeVEthStatsInErrs OBJECT-TYPE
    SYNTAX      Counter32
    MAX-ACCESS  read-only
    STATUS      current
    DESCRIPTION
            "The number of errors received on this interface since interface
            reset"

        ::=     { cBladeVEthStatsEntry 7 }


cBladeVEthStatsInDrops OBJECT-TYPE
    SYNTAX      Counter32
    MAX-ACCESS  read-only
    STATUS      current
    DESCRIPTION
            "The number of dropped incoming packets on this interface since
            interface reset."

        ::=     { cBladeVEthStatsEntry 8 }


cBladeVEthStatsInOverrun OBJECT-TYPE
    SYNTAX      Counter32
    MAX-ACCESS  read-only
    STATUS      current
    DESCRIPTION
            "The number of overrun incoming packets on this interface since
            interface reset."

        ::=     { cBladeVEthStatsEntry 9 }


cBladeVEthStatsInMulticast OBJECT-TYPE
    SYNTAX      Counter32
    MAX-ACCESS  read-only
    STATUS      current
    DESCRIPTION
            "The number of multicast packets received on this interface since
            interface reset."

        ::=     { cBladeVEthStatsEntry 10 }


cBladeVEthStatsOutBytes OBJECT-TYPE
    SYNTAX      Counter32
    MAX-ACCESS  read-only
    STATUS      current
    DESCRIPTION
            "The number of bytes transmitted from this interface since
            interface reset."

        ::=     { cBladeVEthStatsEntry 11 }


cBladeVEthStatsOutPackets OBJECT-TYPE
    SYNTAX      Counter32
    MAX-ACCESS  read-only
    STATUS      current
    DESCRIPTION
            "The number of packets transmitted from this interface since
            interface reset."

        ::=     { cBladeVEthStatsEntry 12 }


cBladeVEthStatsOutErrs OBJECT-TYPE
    SYNTAX      Counter32
    MAX-ACCESS  read-only
    STATUS      current
    DESCRIPTION
            "The number of errors encountered while transmitting from this
            interface since interface reset."

        ::=     { cBladeVEthStatsEntry 13 }


cBladeVEthStatsOutDrops OBJECT-TYPE
    SYNTAX      Counter32
    MAX-ACCESS  read-only
    STATUS      current
    DESCRIPTION
            "The number of dropped packets intended for transmission from this
            interface since interface reset."

        ::=     { cBladeVEthStatsEntry 14 }


cBladeVEthStatsOutOverrun OBJECT-TYPE
    SYNTAX      Counter32
    MAX-ACCESS  read-only
    STATUS      current
    DESCRIPTION
            "The number of overrun packets intended for transmission from this
            interface since interface reset."

        ::=     { cBladeVEthStatsEntry 15 }


cBladeVEthStatsOutCollisions OBJECT-TYPE
    SYNTAX      Counter32
    MAX-ACCESS  read-only
    STATUS      current
    DESCRIPTION
            "The number of collisions detetced while transmitting from this
            interface since interface reset."

        ::=     { cBladeVEthStatsEntry 16 }


cBladeVEthStatsOutCarrierDctFail OBJECT-TYPE
    SYNTAX      Counter32
    MAX-ACCESS  read-only
    STATUS      current
    DESCRIPTION
            "The number of carrier detect failures detetced while transmitting
            from this interface since interface reset."

        ::=     { cBladeVEthStatsEntry 17 }


cBladeVEthStatsOutCompressed OBJECT-TYPE
    SYNTAX      Counter32
    MAX-ACCESS  read-only
    STATUS      current
    DESCRIPTION
            "The number of compressed packets transmitted from this interface
            since interface reset."

        ::=     { cBladeVEthStatsEntry 18 }


cBladeVEthStatsOperStatus OBJECT-TYPE
    SYNTAX      InterfaceOperStatus
    MAX-ACCESS  read-only
    STATUS      current
    DESCRIPTION
            "The operational state of the interface."

        ::=     { cBladeVEthStatsEntry 19 }


-- table of IP addresses assigned to each cBlade Eth (not yet implemented)
cBladeVEthIpTable     OBJECT-TYPE
    SYNTAX      SEQUENCE OF CBladeVEthIpEntry
    MAX-ACCESS  not-accessible
    STATUS      current
    DESCRIPTION
            "A list of IP addresses, broadcast addresses, and nework masks
            configured on each cBlade Eth interface."

        ::=     { cBlades 9 }


cBladeVEthIpEntry     OBJECT-TYPE
    SYNTAX      CBladeVEthIpEntry
    MAX-ACCESS  not-accessible
    STATUS      current
    DESCRIPTION
            "the current IP address, broadcast address, and network mask
            for a pServer Eth cBlade or alias."

    INDEX       { bladeFrameIndex, cBladeIndex, cBladeVEthIndex, cBladeVEthIpAliasName }
        ::=     { cBladeVEthIpTable 1 }


CBladeVEthIpEntry ::=
    SEQUENCE {
        cBladeVEthIpAliasName
            DisplayString,
        cBladeVEthIpVEthIndex
            Integer32,
        cBladeVEthIpCBladeIndex
            Integer32,
        cBladeVEthIpBladeFrameIndex
            Integer32,
        cBladeVEthIpAddress
            IpAddress,
        cBladeVEthIpBroadcast
            IpAddress,
        cBladeVEthIpMask
            IpAddress
    }


cBladeVEthIpAliasName OBJECT-TYPE
    SYNTAX      DisplayString (SIZE(0..63))
    MAX-ACCESS  read-only
    STATUS      current
    DESCRIPTION
            "The name of this network interface or alias, i.e. lo, veth31, eht10:1"

        ::=     { cBladeVEthIpEntry 1 }


cBladeVEthIpVEthIndex OBJECT-TYPE
    SYNTAX      Integer32
    MAX-ACCESS  read-only
    STATUS      current
    DESCRIPTION
            "An integer value identifying the cBladeEthIndex of the cBlade VEth
            that hosts this IP configuraion."

        ::=     { cBladeVEthIpEntry 2 }


cBladeVEthIpCBladeIndex OBJECT-TYPE
    SYNTAX      Integer32
    MAX-ACCESS  read-only
    STATUS      current
    DESCRIPTION
            "An integer value identifying the cBladeIndex of the cBlade
            that hosts this IP configuraion."

        ::=     { cBladeVEthIpEntry 3 }


cBladeVEthIpBladeFrameIndex OBJECT-TYPE
    SYNTAX      Integer32
    MAX-ACCESS  read-only
    STATUS      current
    DESCRIPTION
            "An integer value identifying the bladeFrameIndex of the
            BladeFrame that hosts this IP configuraion."

        ::=     { cBladeVEthIpEntry 4 }


cBladeVEthIpAddress OBJECT-TYPE
    SYNTAX      IpAddress
    MAX-ACCESS  read-only
    STATUS      current
    DESCRIPTION
            "The IP address configured on this pServer eth (or alias)"

        ::=     { cBladeVEthIpEntry 5 }


cBladeVEthIpBroadcast OBJECT-TYPE
    SYNTAX      IpAddress
    MAX-ACCESS  read-only
    STATUS      current
    DESCRIPTION
            "The broadcast address configured on this pServer eth (or alias)"

        ::=     { cBladeVEthIpEntry 6 }


cBladeVEthIpMask OBJECT-TYPE
    SYNTAX      IpAddress
    MAX-ACCESS  read-only
    STATUS      current
    DESCRIPTION
            "The network mask configured on this pServer eth (or alias)"

        ::=     { cBladeVEthIpEntry 7 }


-- table of cBlade HW controls

cBladeControlTable  OBJECT-TYPE
    SYNTAX      SEQUENCE OF CBladeControlEntry
    MAX-ACCESS  not-accessible
    STATUS      current
    DESCRIPTION
            "A list of cBlade entries containing controls for Control
            Blades in discovered Egenera BladeFrames."

        ::=     { cBlades 10 }


cBladeControlEntry OBJECT-TYPE
    SYNTAX      CBladeControlEntry
    MAX-ACCESS  not-accessible
    STATUS      current
    DESCRIPTION
            "An cBlade Control entry contains controls for Control
            Blades in the Egenera PAN."

    INDEX       { bladeFrameIndex, cBladeIndex }
        ::=     { cBladeControlTable 1 }


CBladeControlEntry ::=
    SEQUENCE {
        cBladeControlPowerUp
            Integer32,
        cBladeControlPowerDown
            Integer32,
        cBladeControlColdReset
            Integer32,
        cBladeControlWarmReset
            Integer32,
        cBladeControlNmi
            Integer32,
        cBladeControlSwitchPowerUp
            Integer32,
        cBladeControlSwitchPowerDown
            Integer32,
        cBladeControlSwitchPowerCycle
            Integer32
    }


cBladeControlPowerUp OBJECT-TYPE
    SYNTAX      Integer32
    MAX-ACCESS  read-write
    STATUS      current
    DESCRIPTION
            "When set to 1, initiates a power up operation on this Control
            Blade.  When read, returns 0."

        ::=     { cBladeControlEntry 1 }


cBladeControlPowerDown OBJECT-TYPE
    SYNTAX      Integer32
    MAX-ACCESS  read-write
    STATUS      current
    DESCRIPTION
            "When set to 1, initiates a power down operation on this Control
            Blade.  When read, returns 0."

        ::=     { cBladeControlEntry 2 }


cBladeControlColdReset OBJECT-TYPE
    SYNTAX      Integer32
    MAX-ACCESS  read-write
    STATUS      current
    DESCRIPTION
            "When set to 1, initiates a cold reset operation on this Control
            Blade. When read, returns 0."

        ::=     { cBladeControlEntry 3 }


cBladeControlWarmReset OBJECT-TYPE
    SYNTAX  Integer32
    MAX-ACCESS  read-write
    STATUS  current
    DESCRIPTION
            "When set to 1, initiates a warm reset operation on this Control
            Blade.  When read, returns 0."

        ::=     { cBladeControlEntry 4 }


cBladeControlNmi OBJECT-TYPE
    SYNTAX      Integer32
    MAX-ACCESS  read-write
    STATUS      current
    DESCRIPTION
            "When set to 1, initiates an non-maskable interrupt operation on
            this cBlade. When read, returns 0."

        ::=     { cBladeControlEntry 5 }


cBladeControlSwitchPowerUp OBJECT-TYPE
    SYNTAX      Integer32
    MAX-ACCESS  read-write
    STATUS      current
    DESCRIPTION
            "When set to 1, initiates a power down operation on the switch
            component of this cBlade.  When read, returns 0."

        ::=     { cBladeControlEntry 6 }


cBladeControlSwitchPowerDown OBJECT-TYPE
    SYNTAX      Integer32
    MAX-ACCESS  read-write
    STATUS      current
    DESCRIPTION
            "When set to 1, initiates a power up operation on the switch
            component of this cBlade.  When read, returns 0."

        ::=     { cBladeControlEntry 7 }


cBladeControlSwitchPowerCycle  OBJECT-TYPE
    SYNTAX      Integer32
    MAX-ACCESS  read-write
    STATUS      current
    DESCRIPTION
            "When set to 1, initiates a power cycle operation on the switch
            component of this cBlade.  When read, returns 0."

        ::=     { cBladeControlEntry 8 }


-- cBlade Hardware Monitors

HardwareMonitorType ::= TEXTUAL-CONVENTION
    STATUS      current
    DESCRIPTION
            "Describes hardware monitor types."
    SYNTAX INTEGER {
        voltage(1),
        temperature(2),
        fanspeed(3),
        undefined(999)
}

cBladeHwMonitorTable OBJECT-TYPE
    SYNTAX      SEQUENCE OF CBladeMonitorEntry
    MAX-ACCESS      not-accessible
    STATUS      current
    DESCRIPTION
            "A list of cBlade monitor entries for each cBlade in the PAN.
            Voltage is measured in Volts, Temperature in degrees Celcius,
            and fan speed in Revolutions Per Minute"

        ::=     { cBlades 11 }


cBladeMonitorEntry OBJECT-TYPE
    SYNTAX      CBladeMonitorEntry
    MAX-ACCESS      not-accessible
    STATUS      current
    DESCRIPTION
            "Attributes of a specific cBlade hardware monitor."


    INDEX       { bladeFrameIndex, cBladeIndex, cBladeHwMonitorIndex }
        ::=     { cBladeHwMonitorTable 1 }


CBladeMonitorEntry ::=
    SEQUENCE {
        cBladeHwMonitorIndex
            Integer32,
        cBladeHwMonitorName
            DisplayString,
        cBladeHwMonitorType
            HardwareMonitorType,
        cBladeHwMonitorValue
            Integer32,
        cBladeHwMonitorValueDenomonator
            Integer32
    }


cBladeHwMonitorIndex OBJECT-TYPE
    SYNTAX      Integer32 (1..2147483647)
    MAX-ACCESS  read-only
    STATUS      current
    DESCRIPTION
            "An integer value uniquely identifying the monitor within the
            cBlade."

        ::=     { cBladeMonitorEntry 1 }


cBladeHwMonitorName OBJECT-TYPE
    SYNTAX      DisplayString
    MAX-ACCESS  read-only
    STATUS      current
    DESCRIPTION
            "An String identifying the name of the hardware monitor."

        ::=     { cBladeMonitorEntry 2 }


cBladeHwMonitorType OBJECT-TYPE
    SYNTAX      HardwareMonitorType
    MAX-ACCESS  read-only
    STATUS      current
    DESCRIPTION
            "An integer encoding of the monitor type; voltage, temperature, or
            fanspeed."

        ::=     { cBladeMonitorEntry 3 }


cBladeHwMonitorValue OBJECT-TYPE
    SYNTAX      Integer32
    MAX-ACCESS  read-only
    STATUS      current
    DESCRIPTION
            "The integer representation of the current hardware sensor value.
            Voltage values are multiplied by 100 and rounted to convert from
            float to integer.  Thus 0.530 => 53"

        ::=     { cBladeMonitorEntry 4 }


cBladeHwMonitorValueDenomonator OBJECT-TYPE
    SYNTAX      Integer32
    MAX-ACCESS      read-only
    STATUS      current
    DESCRIPTION
            "The integer representation of the denomonator required to convert
            the integer incoding of the sensor value to the float value.
            For voltage sensors, this value is 100, for all other sensors,
            this value is 1."

        ::=     { cBladeMonitorEntry 5 }

cBladeHbaTable   OBJECT-TYPE
    SYNTAX      SEQUENCE OF CBladeHbaEntry
    MAX-ACCESS  not-accessible
    STATUS      current
    DESCRIPTION
            "physical HBA on a BladeFrame's cBlades (cBlades)."


        ::=     { cBlades 12 }


cBladeHbaEntry OBJECT-TYPE
    SYNTAX      CBladeHbaEntry
    MAX-ACCESS  not-accessible
    STATUS      current
    DESCRIPTION
            "Information specific to each HBA in the PAN."

    INDEX       { bladeFrameIndex, cBladeIndex, cBladeHbaIndex }
        ::=     { cBladeHbaTable 1 }

CBladeHbaEntry ::=
    SEQUENCE {
        cBladeHbaIndex
            Integer32,
        cBladeHbaCBladeIndex
            Integer32,
        cBladeHbaBladeFrameIndex
            Integer32,
        cBladeHbaName
            DisplayString,
        cBladeHbaStatus
            DisplayString,
        cBladeHbaEnableState
            TruthValue
    }

cBladeHbaIndex OBJECT-TYPE
    SYNTAX      Integer32 (1..2147483647)
    MAX-ACCESS  read-only
    STATUS      current
    DESCRIPTION
            "An integer value uniquely identifying the HBA within the
            cBlade."

        ::=     { cBladeHbaEntry 1 }


cBladeHbaCBladeIndex OBJECT-TYPE
    SYNTAX      Integer32 (1..2147483647)
    MAX-ACCESS  read-only
    STATUS      current
    DESCRIPTION
            "An integer value identifying the cBladeIndex value of the
            cBlade that hosts this HBA."

        ::=     { cBladeHbaEntry 2 }


cBladeHbaBladeFrameIndex OBJECT-TYPE
    SYNTAX      Integer32 (1..2147483647)
    MAX-ACCESS  read-only
    STATUS      current
    DESCRIPTION
            "An integer value identifying the bladeFrameIndex value of the
            BladeFrame that hosts this HBA."

        ::=     { cBladeHbaEntry 3 }

cBladeHbaName OBJECT-TYPE
    SYNTAX      DisplayString
    MAX-ACCESS  read-only
    STATUS      current
    DESCRIPTION
            "A human readable string uniquely identifying the cBlade HBA."

        ::=     { cBladeHbaEntry 4 }


cBladeHbaStatus OBJECT-TYPE
    SYNTAX      DisplayString
    MAX-ACCESS  read-only
    STATUS      current
    DESCRIPTION
            "A human readable string identifying the status of the cBlade HBA."

        ::=     { cBladeHbaEntry 5 }

cBladeHbaEnableState OBJECT-TYPE
    SYNTAX      TruthValue
    MAX-ACCESS  read-only
    STATUS      current
    DESCRIPTION
            "Indicates whether the cBlade HBA is enabled."

        ::=     { cBladeHbaEntry 6 }


-- sBlades group

sBlades OBJECT IDENTIFIER ::= { blades 2 }

-- sBlade table
-- The sBlade table contains information about sBlades in each
-- BladeFrame.

sBladeTable OBJECT-TYPE
    SYNTAX      SEQUENCE OF SBladeEntry
    MAX-ACCESS  not-accessible
    STATUS      current
    DESCRIPTION
            "A list of sBlade entries containing information for Switch
            Blades in the Egenera PAN."

        ::=     { sBlades 1 }


sBladeEntry OBJECT-TYPE
    SYNTAX      SBladeEntry
    MAX-ACCESS  not-accessible
    STATUS      current
    DESCRIPTION
            "A sBlade entry contains information for sBlades in
            the Egenera PAN."

    INDEX       { bladeFrameIndex, sBladeIndex }
        ::=     { sBladeTable 1 }


SBladeEntry ::=
    SEQUENCE {
        sBladeIndex
            Integer32,
        sBladeFrameIndex
            Integer32,
        sBladeName
            DisplayString,
        sBladeSerialNumber
            DisplayString,
        sBladePartNumber
            DisplayString,
        sBladePowerStatus
            PowerStatusType,
        sBladePowerSupply
            DisplayString,
        sBladeMasterStatus
            TruthValue,
        sBladeActiveStatus
            TruthValue,
        sBladeEnabledStatus
            TruthValue,
        sBladeSelectedStatus
            TruthValue,
        sBladeRecognizedStatus
            TruthValue,
        sBladeHealthStatus
            HealthStatusType,
        sBladeUpTime
            TimeTicks
    }


sBladeIndex OBJECT-TYPE
    SYNTAX      Integer32 (1..2147483647)
    MAX-ACCESS  read-only
    STATUS      current
    DESCRIPTION
            "An integer value uniquely identifying the sBlade within the
            BladeFrame.  This corresponds to the physical location of the
            sBlade within the BladeFrame."

        ::=     { sBladeEntry 1 }


sBladeFrameIndex OBJECT-TYPE
    SYNTAX      Integer32 (1..2147483647)
    MAX-ACCESS  read-only
    STATUS      current
    DESCRIPTION
            "An integer value identifying the bladeFrameIndex value of the
            BladeFrame that hosts this sBlade."

        ::=     { sBladeEntry 2 }


sBladeName OBJECT-TYPE
    SYNTAX      DisplayString
    MAX-ACCESS  read-only
    STATUS      current
    DESCRIPTION
            "A textual string identifying the sBlade."

        ::=     { sBladeEntry 3 }


sBladeSerialNumber OBJECT-TYPE
    SYNTAX      DisplayString
    MAX-ACCESS  read-only
    STATUS      current
    DESCRIPTION
            "Describes the serial number of this sBlade."

        ::=     { sBladeEntry 4 }


sBladePartNumber OBJECT-TYPE
    SYNTAX      DisplayString
    MAX-ACCESS  read-only
    STATUS      current
    DESCRIPTION
            "Describes the part number of this sBlade."

        ::=     { sBladeEntry 5 }


sBladePowerStatus OBJECT-TYPE
    SYNTAX      PowerStatusType
    MAX-ACCESS  read-only
    STATUS      current
    DESCRIPTION
            "The power status of the sBlade."

        ::=     { sBladeEntry 6 }


sBladePowerSupply OBJECT-TYPE
    SYNTAX      DisplayString
    MAX-ACCESS  read-only
    STATUS      current
    DESCRIPTION
            "The name of the power supply used by this sBlade."

        ::=     { sBladeEntry 7 }

sBladeMasterStatus OBJECT-TYPE
    SYNTAX      TruthValue
    MAX-ACCESS  read-only
    STATUS      current
    DESCRIPTION
            "Indicates that the switch is acting as the master switch."

        ::=     { sBladeEntry 8 }


sBladeActiveStatus OBJECT-TYPE
    SYNTAX      TruthValue
    MAX-ACCESS  read-only
    STATUS      current
    DESCRIPTION
            "Indicates whether or not the sBlade is active."

        ::=     { sBladeEntry 9 }


sBladeEnabledStatus OBJECT-TYPE
    SYNTAX      TruthValue
    MAX-ACCESS  read-only
    STATUS      current
    DESCRIPTION
            "Indicates whether the sBlade is enabled or disabled."

        ::=     { sBladeEntry 10 }


sBladeSelectedStatus OBJECT-TYPE
    SYNTAX      TruthValue
    MAX-ACCESS  read-only
    STATUS      current
    DESCRIPTION
            "Indicates whether the sBlade is selected."

        ::=     { sBladeEntry 11 }


sBladeRecognizedStatus OBJECT-TYPE
    SYNTAX      TruthValue
    MAX-ACCESS  read-only
    STATUS      current
    DESCRIPTION
            "Indicates whether the blade has been recognized by the PAN Manager."

        ::=     { sBladeEntry 12 }


sBladeHealthStatus OBJECT-TYPE
    SYNTAX      HealthStatusType
    MAX-ACCESS  read-only
    STATUS      current
    DESCRIPTION
            "An indication of the health of the BladeFrame."

        ::=     { sBladeEntry 13 }


sBladeUpTime OBJECT-TYPE
    SYNTAX      TimeTicks
    MAX-ACCESS  read-only
    STATUS      current
    DESCRIPTION
            "The amount of time that the BladeFrame has been up."

        ::=     { sBladeEntry 14 }


-- Switch controls

sBladeControlTable OBJECT-TYPE
    SYNTAX      SEQUENCE OF SBladeControlEntry
    MAX-ACCESS  not-accessible
    STATUS      current
    DESCRIPTION
            "A list of sBlade Control entries containing controls for
            sBlades the Egenera PAN."

        ::=     { sBlades 2 }


sBladeControlEntry OBJECT-TYPE
    SYNTAX      SBladeControlEntry
    MAX-ACCESS  not-accessible
    STATUS      current
    DESCRIPTION
            "A sBlade Control entry contains controls for sBlades
            in the Egenera PAN."

    INDEX       { bladeFrameIndex, sBladeIndex }
        ::=     { sBladeControlTable 1 }


SBladeControlEntry ::=
    SEQUENCE {
        sBladeControlPowerUp
            Integer32,
        sBladeControlPowerDown
            Integer32
    }


sBladeControlPowerUp OBJECT-TYPE
    SYNTAX      Integer32
    MAX-ACCESS  read-write
    STATUS      current
    DESCRIPTION
            "When set to 1, initiates a power up operation on this
            sBlade.  When read, returns 0."

        ::=     { sBladeControlEntry 1 }


sBladeControlPowerDown OBJECT-TYPE
    SYNTAX      Integer32
    MAX-ACCESS  read-write
    STATUS      current
    DESCRIPTION
            "When set to 1, initiates a power down operation on this
            sBlade.  When read, returns 0."

        ::=     { sBladeControlEntry 2 }

-- sBlade hardware monitors

sBladeHwMonitorTable OBJECT-TYPE
    SYNTAX      SEQUENCE OF SBladeMonitorEntry
    MAX-ACCESS  not-accessible
    STATUS      current
    DESCRIPTION
            "A list of sBlade monitor entries for each sBlade in the PAN."

        ::=     { sBlades 3 }


sBladeMonitorEntry OBJECT-TYPE
    SYNTAX      SBladeMonitorEntry
    MAX-ACCESS  not-accessible
    STATUS      current
    DESCRIPTION
            "Attributes of a specific sBlade hardware monitor."


    INDEX       { bladeFrameIndex, sBladeIndex, sBladeHwMonitorIndex }
        ::=     { sBladeHwMonitorTable 1 }


SBladeMonitorEntry ::=
    SEQUENCE {
        sBladeHwMonitorIndex
            Integer32,
        sBladeHwMonitorName
            DisplayString,
        sBladeHwMonitorType
            HardwareMonitorType,
        sBladeHwMonitorValue
            Integer32,
        sBladeHwMonitorValueDenomonator
            Integer32
    }


sBladeHwMonitorIndex OBJECT-TYPE
    SYNTAX      Integer32 (1..2147483647)
    MAX-ACCESS  read-only
    STATUS      current
    DESCRIPTION
            "An integer value uniquely identifying the monitor within the
            sBlade."

        ::=     { sBladeMonitorEntry 1 }


sBladeHwMonitorName OBJECT-TYPE
    SYNTAX      DisplayString
    MAX-ACCESS  read-only
    STATUS      current
    DESCRIPTION
            "An String identifying the name of the hardware monitor."

        ::=     { sBladeMonitorEntry 2 }


sBladeHwMonitorType OBJECT-TYPE
    SYNTAX      HardwareMonitorType
    MAX-ACCESS  read-only
    STATUS      current
    DESCRIPTION
            "An integer encoding of the monitor type; voltage, temperature, or
            fanspeed."

        ::=     { sBladeMonitorEntry 3 }


sBladeHwMonitorValue OBJECT-TYPE
    SYNTAX      Integer32
    MAX-ACCESS  read-only
    STATUS      current
    DESCRIPTION
            "The integer representation of the current hardware sensor value.
            Voltage values are multiplied by 100 and rounted to convert from
            float to integer.  Thus 0.530 => 53"

        ::=     { sBladeMonitorEntry 4 }


sBladeHwMonitorValueDenomonator OBJECT-TYPE
    SYNTAX      Integer32
    MAX-ACCESS  read-only
    STATUS      current
    DESCRIPTION
            "The integer representation of the denomonator required to convert
            the integer incoding of the sensor value to the float value.
            For voltage sensors, this value is 100, for all other sensors,
            this value is 1."

        ::=     { sBladeMonitorEntry 5 }



sBladeEthTable   OBJECT-TYPE
    SYNTAX      SEQUENCE OF SBladeEthEntry
    MAX-ACCESS  not-accessible
    STATUS      current
    DESCRIPTION
            "physical Network Interface Cards (NICs) on a BladeFrame's
                   sBlades (sBlades)."

        ::=     { sBlades 4 }


sBladeEthEntry OBJECT-TYPE
    SYNTAX      SBladeEthEntry
    MAX-ACCESS  not-accessible
    STATUS      current
    DESCRIPTION
            "Information specific to each sBlade Eth in the PAN."

    INDEX       { bladeFrameIndex, sBladeIndex, sBladeEthIndex }
        ::=     { sBladeEthTable 1 }

SBladeEthEntry ::=
    SEQUENCE {
        sBladeEthIndex
            Integer32,
        sBladeEthSBladeIndex
            Integer32,
        sBladeEthBladeFrameIndex
            Integer32,
        sBladeEthName
            DisplayString,
        sBladeEthFullName
            DisplayString,
        sBladeEthHwMACAddressOctets
            PhysAddress,
        sBladeEthHwMACAddressString
            DisplayString,
        sBladeEthNICType
            DisplayString,
        sBladeEthFiltered
            TruthValue,
        sBladeEthLinkState
            InterfaceOperStatus,
        sBladeEthRethStatus
            EthRethStatus
    }

sBladeEthIndex OBJECT-TYPE
    SYNTAX      Integer32 (1..2147483647)
    MAX-ACCESS  read-only
    STATUS      current
    DESCRIPTION
            "An integer value uniquely identifying the sBlade within the
            sBlade."

        ::=     { sBladeEthEntry 1 }


sBladeEthSBladeIndex OBJECT-TYPE
    SYNTAX      Integer32 (1..2147483647)
    MAX-ACCESS  read-only
    STATUS      current
    DESCRIPTION
            "An integer value identifying the sBladeIndex value of the
            sBlade that hosts this Eth."

        ::=     { sBladeEthEntry 2 }


sBladeEthBladeFrameIndex OBJECT-TYPE
    SYNTAX      Integer32 (1..2147483647)
    MAX-ACCESS  read-only
    STATUS      current
    DESCRIPTION
            "An integer value identifying the bladeFrameIndex value of the
            BladeFrame that hosts this Eth."

        ::=     { sBladeEthEntry 3 }


sBladeEthName OBJECT-TYPE
    SYNTAX      DisplayString
    MAX-ACCESS  read-only
    STATUS      current
    DESCRIPTION
            "A human readable string uniquely identifying the sBlade Eth."

        ::=     { sBladeEthEntry 4 }


sBladeEthFullName OBJECT-TYPE
    SYNTAX      DisplayString
    MAX-ACCESS  read-only
    STATUS      current
    DESCRIPTION
            "A human readable string uniquely identifying the sBlade Eth,
            including the host sBlade and BladeFrame."

        ::=     { sBladeEthEntry 5 }


sBladeEthHwMACAddressOctets OBJECT-TYPE
    SYNTAX      PhysAddress
    MAX-ACCESS  read-only
    STATUS      current
    DESCRIPTION
            "An encoding of the sBlade Eth hardware MAC address."

        ::=     { sBladeEthEntry 6 }


sBladeEthHwMACAddressString OBJECT-TYPE
    SYNTAX      DisplayString
    MAX-ACCESS  read-only
    STATUS      current
    DESCRIPTION
            "A human readable string representing the sBlade Eth hardware
            MAC address in the form: '6E:4A:1F:00:01:06'."

        ::=     { sBladeEthEntry 7 }



sBladeEthNICType OBJECT-TYPE
    SYNTAX      DisplayString
    MAX-ACCESS  read-only
    STATUS      current
    DESCRIPTION
            "Specifies the sBlade ETH NIC type, such as e100 or e1000."

        ::=     { sBladeEthEntry 10 }


sBladeEthFiltered OBJECT-TYPE
    SYNTAX      TruthValue
    MAX-ACCESS  read-only
    STATUS      current
    DESCRIPTION
            "indicates whether filtered mode is enabled.  unfiltered mode
            allows the sBlade NICs to admit all external network traffic sent
            by their connecting switch. Filtered mode enables the sBlade
            NICs to filter incoming traffic  based  on  a  single  MAC
            address assigned to the NIC. Unfiltered mode is the default
            configuration. "

        ::=     { sBladeEthEntry 11 }

sBladeEthLinkState OBJECT-TYPE
    SYNTAX      InterfaceOperStatus
    MAX-ACCESS  read-only
    STATUS      current
    DESCRIPTION
            "The Link State of the Eth."

        ::=     { sBladeEthEntry 14 }


sBladeEthRethStatus OBJECT-TYPE
    SYNTAX      EthRethStatus
    MAX-ACCESS  read-only
    STATUS      current
    DESCRIPTION
            "The State of the Eth with respect to REth membership."

        ::=     { sBladeEthEntry 15 }





-- pBlades group

pBlades OBJECT IDENTIFIER ::= { blades 3 }

-- pBlade table
-- The pBlade table contains information about pBlades in
-- BladeFrames.

pBladeTable OBJECT-TYPE
    SYNTAX      SEQUENCE OF PBladeEntry
    MAX-ACCESS  not-accessible
    STATUS      current
    DESCRIPTION
            "A list of pBlade entries containing information
            for pBlades the Egenera PAN."

        ::=     { pBlades 1 }


pBladeEntry OBJECT-TYPE
    SYNTAX      PBladeEntry
    MAX-ACCESS  not-accessible
    STATUS      current
    DESCRIPTION
            "An pBlade entry contains information for Processing
            Blades in the Egenera PAN."

    INDEX       { bladeFrameIndex, pBladeIndex }
        ::=     { pBladeTable 1 }


PBladeEntry ::=
    SEQUENCE {
        pBladeIndex
            Integer32,
        pBladeFrameIndex
            Integer32,
        pBladePServerIndex
            Integer32,
        pBladeLPanIndex
            Integer32,
        pBladeName
            DisplayString,
        pBladeBladeFrameName
            DisplayString,
        pBladePServerName
            DisplayString,
        pBladeLPanName
            DisplayString,
        pBladeDescription
            DisplayString,
        pBladeHostName
            DisplayString,
        pBladeNumCpus
            Integer32,
        pBladeCpuSpeed
            Integer32,
        pBladeCpuModel
            DisplayString,
        pBladeMemorySize
            Integer32,
        pBladeCache
            Integer32,
        pBladeArchitecture
            DisplayString,
        pBladeSerialNumber
            DisplayString,
        pBladePartNumber
            DisplayString,
        pBladePowerStatus
            PowerStatusType,
        pBladePowerSupply
            DisplayString,
        pBladeActiveStatus
            TruthValue,
        pBladeAllocationStatus
            TruthValue,
        pBladeEnabledStatus
            TruthValue,
        pBladeSelectedStatus
            TruthValue,
        pBladeRecognizedStatus
            TruthValue,
        pBladeHealthStatus
            HealthStatusType,
        pBladeInDebugger
            TruthValue,
        pBladeOutOfService
            TruthValue,
        pBladeOutOfServicePending
            TruthValue,
        pBladeBootStatus
            DisplayString,
        pBladeUpTime
            TimeTicks,
        pBladePoolIndex
            Integer32
    }


pBladeIndex OBJECT-TYPE
    SYNTAX      Integer32 (1..2147483647)
    MAX-ACCESS  read-only
    STATUS      current
    DESCRIPTION
            "An integer value uniquely identifying the pBlade within
            the BladeFrame.  This corresponds to the physical location of the
            pBlade within the BladeFrame."

        ::=     { pBladeEntry 1 }


pBladeFrameIndex OBJECT-TYPE
    SYNTAX      Integer32 (1..2147483647)
    MAX-ACCESS  read-only
    STATUS      current
    DESCRIPTION
            "An integer value identifying the bladeFrameIndex value of the
            BladeFrame that hosts this pBlade."

        ::=     { pBladeEntry 2 }


pBladePServerIndex OBJECT-TYPE
    SYNTAX      Integer32 (1..2147483647)
    MAX-ACCESS  read-only
    STATUS      current
    DESCRIPTION
            "An integer value identifying the pServerIndex of the pServer
            running on this pBlade, or -1 if the pBlade is not occupied
            by a pServer."

        ::=     { pBladeEntry 3 }


pBladeLPanIndex OBJECT-TYPE
    SYNTAX      Integer32 (1..2147483647)
    MAX-ACCESS  read-only
    STATUS      current
    DESCRIPTION
            "An integer value identifying the lPanIndex of the LPAN
            containing the pServer running on this pBlade, or -1 if the
            pBlade is not occupied by a pServer."

        ::=     { pBladeEntry 4 }


pBladeName OBJECT-TYPE
    SYNTAX      DisplayString
    MAX-ACCESS  read-only
    STATUS      current
    DESCRIPTION
            "A textual string identifying this pBlade."

        ::=     { pBladeEntry 5 }


pBladeBladeFrameName OBJECT-TYPE
    SYNTAX      DisplayString
    MAX-ACCESS  read-only
    STATUS      current
    DESCRIPTION
            "A textual string identifying the BladeFrame containing this
            pBlade."

        ::=     { pBladeEntry 6 }


pBladePServerName OBJECT-TYPE
    SYNTAX      DisplayString
    MAX-ACCESS  read-only
    STATUS      current
    DESCRIPTION
            "A textual string identifying the pServer running on this pBlade."

        ::=     { pBladeEntry 7 }

pBladeLPanName OBJECT-TYPE
    SYNTAX      DisplayString
    MAX-ACCESS  read-only
    STATUS      current
    DESCRIPTION
            "A textual string identifying the LPAN containing the pServer
            running on this pBlade."

        ::=     { pBladeEntry 8 }


pBladeDescription OBJECT-TYPE
    SYNTAX      DisplayString
    MAX-ACCESS  read-only
    STATUS      current
    DESCRIPTION
            "A textual string describing this pBlade."

        ::=     { pBladeEntry 9 }


pBladeHostName OBJECT-TYPE
    SYNTAX      DisplayString
    MAX-ACCESS  read-only
    STATUS      current
    DESCRIPTION
            "The hostname of the PServer running on this pBlade."

        ::=     { pBladeEntry 10 }


pBladeNumCpus OBJECT-TYPE
    SYNTAX      Integer32
    MAX-ACCESS  read-only
    STATUS      current
    DESCRIPTION
            "The number of CPUs on the pBlade."

        ::=     { pBladeEntry 11 }


pBladeCpuSpeed OBJECT-TYPE
    SYNTAX      Integer32
    MAX-ACCESS  read-only
    STATUS      current
    DESCRIPTION
            "The speed of the CPUs on the pBlade in Mhz."

        ::=     { pBladeEntry 12 }


pBladeCpuModel OBJECT-TYPE
    SYNTAX      DisplayString
    MAX-ACCESS  read-only
    STATUS      current
    DESCRIPTION
            "A textual string representing the CPU model this pBlade."

        ::=     { pBladeEntry 13 }


pBladeMemorySize OBJECT-TYPE
    SYNTAX      Integer32
    MAX-ACCESS  read-only
    STATUS      current
    DESCRIPTION
            "The size of the physical RAM installed on the pBlade,
            in MB."

        ::=     { pBladeEntry 14 }


pBladeCache OBJECT-TYPE
    SYNTAX      Integer32
    MAX-ACCESS  read-only
    STATUS      current
    DESCRIPTION
            "The size of the CPU cache installed on the pBlade,
            in kB."

        ::=     { pBladeEntry 15 }


pBladeArchitecture OBJECT-TYPE
    SYNTAX      DisplayString
    MAX-ACCESS  read-only
    STATUS      current
    DESCRIPTION
            "Describes the pBlade hardware architecture."

        ::=     { pBladeEntry 16 }


pBladeSerialNumber OBJECT-TYPE
    SYNTAX      DisplayString
    MAX-ACCESS  read-only
    STATUS      current
    DESCRIPTION
            "Describes the serial number of this pBlade."

        ::=     { pBladeEntry 17 }


pBladePartNumber OBJECT-TYPE
    SYNTAX      DisplayString
    MAX-ACCESS  read-only
    STATUS      current
    DESCRIPTION
            "Describes the part number of this pBlade."

        ::=     { pBladeEntry 18 }


pBladePowerStatus OBJECT-TYPE
    SYNTAX      PowerStatusType
    MAX-ACCESS  read-only
    STATUS      current
    DESCRIPTION
            "The power status of the pBlade."

        ::=     { pBladeEntry 19 }


pBladePowerSupply OBJECT-TYPE
    SYNTAX      DisplayString
    MAX-ACCESS  read-only
    STATUS      current
    DESCRIPTION
            "The name of the power supply used by this pBlade."

        ::=     { pBladeEntry 20 }


pBladeActiveStatus OBJECT-TYPE
    SYNTAX      TruthValue
    MAX-ACCESS  read-only
    STATUS      current
    DESCRIPTION
            "Indicates whether or not the blade is active."

        ::=     { pBladeEntry 21 }


pBladeAllocationStatus OBJECT-TYPE
    SYNTAX      TruthValue
    MAX-ACCESS  read-only
    STATUS      current
    DESCRIPTION
            "Indicates whether or not the blade is allocated."

        ::=     { pBladeEntry 22 }


pBladeEnabledStatus OBJECT-TYPE
    SYNTAX      TruthValue
    MAX-ACCESS  read-only
    STATUS      current
    DESCRIPTION
            "Indicates whether the blade is enabled or disabled."

        ::=     { pBladeEntry 23 }


pBladeSelectedStatus OBJECT-TYPE
    SYNTAX      TruthValue
    MAX-ACCESS  read-only
    STATUS      current
    DESCRIPTION
            "Indicates whether the blade is selected."

        ::=     { pBladeEntry 24 }


pBladeRecognizedStatus OBJECT-TYPE
    SYNTAX      TruthValue
    MAX-ACCESS  read-only
    STATUS      current
    DESCRIPTION
            "Indicates whether the blade has been recognized by the PAN Manager."

        ::=     { pBladeEntry 25 }


pBladeHealthStatus OBJECT-TYPE
    SYNTAX      HealthStatusType
    MAX-ACCESS  read-only
    STATUS      current
    DESCRIPTION
            "An indication of the health of the BladeFrame."

        ::=     { pBladeEntry 26 }


pBladeInDebugger OBJECT-TYPE
    SYNTAX      TruthValue
    MAX-ACCESS  read-only
    STATUS      current
    DESCRIPTION
            "Indicates whether or not the kernel kernel on the pBlade has
            entered the debugger."

        ::=     { pBladeEntry 27 }


pBladeOutOfService OBJECT-TYPE
    SYNTAX      TruthValue
    MAX-ACCESS  read-only
    STATUS      current
    DESCRIPTION
            "Indicates whether this pBlade has been designated 'Out Of
            Service'."

        ::=     { pBladeEntry 28 }


pBladeOutOfServicePending OBJECT-TYPE
    SYNTAX      TruthValue
    MAX-ACCESS  read-only
    STATUS      current
    DESCRIPTION
            "Indicates whether this pBlade has a pending designation of
            'Out Of Service'."

        ::=     { pBladeEntry 29 }


pBladeBootStatus OBJECT-TYPE
    SYNTAX      DisplayString
    MAX-ACCESS  read-only
    STATUS      current
    DESCRIPTION
            "Indicates the boot status of this pBlade."

        ::=     { pBladeEntry 30 }


pBladeUpTime OBJECT-TYPE
    SYNTAX      TimeTicks
    MAX-ACCESS  read-only
    STATUS      current
    DESCRIPTION
            "The amount of time that the BladeFrame has been up."

        ::=     { pBladeEntry 31 }


pBladePoolIndex OBJECT-TYPE
    SYNTAX      Integer32 (1..2147483647)
    MAX-ACCESS  read-only
    STATUS      current
    DESCRIPTION
            "An integer value identifying the poolindex of the pool containing
             the pBlade ."

        ::=     { pBladeEntry 32 }


-- pBlade controls

pBladeControlTable OBJECT-TYPE
    SYNTAX      SEQUENCE OF PBladeControlEntry
    MAX-ACCESS  not-accessible
    STATUS      current
    DESCRIPTION
            "A list of pBlade entries containing controls for
            pBlades in the Egenera PAN."

        ::=     { pBlades 2 }


pBladeControlEntry OBJECT-TYPE
    SYNTAX      PBladeControlEntry
    MAX-ACCESS  not-accessible
    STATUS      current
    DESCRIPTION
            "An pBlade entry contains controls for Processing
            Blades in the Egenera PAN."


    INDEX       { bladeFrameIndex, pBladeIndex }
        ::=     { pBladeControlTable 1 }


PBladeControlEntry ::=
    SEQUENCE {
        pBladeControlPowerUp
            Integer32,
        pBladeControlPowerDown
            Integer32,
        pBladeControlColdReset
            Integer32,
        pBladeControlWarmReset
            Integer32,
        pBladeControlNmi
            Integer32
    }


pBladeControlPowerUp OBJECT-TYPE
    SYNTAX      Integer32
    MAX-ACCESS  read-write
    STATUS      current
    DESCRIPTION
            "When set to 1, initiates a power up operation on this Processing
            Blade. When read, returns 0."

        ::=     { pBladeControlEntry 1 }


pBladeControlPowerDown OBJECT-TYPE
    SYNTAX      Integer32
    MAX-ACCESS  read-write
    STATUS      current
    DESCRIPTION
            "When set to 1, initiates a power down operation on this
            pBlade. When read, returns 0."

        ::=     { pBladeControlEntry 2 }


pBladeControlColdReset OBJECT-TYPE
    SYNTAX      Integer32
    MAX-ACCESS  read-write
    STATUS      current
    DESCRIPTION
            "When set to 1, initiates a cold reset operation on this
            pBlade. When read, returns 0."

        ::=     { pBladeControlEntry 3 }


pBladeControlWarmReset OBJECT-TYPE
    SYNTAX      Integer32
    MAX-ACCESS  read-write
    STATUS      current
    DESCRIPTION
            "When set to 1, initiates a warm reset operation on this
            pBlade. When read, returns 0."

        ::=     { pBladeControlEntry 4 }


pBladeControlNmi OBJECT-TYPE
    SYNTAX      Integer32
    MAX-ACCESS  read-write
    STATUS      current
    DESCRIPTION
            "When set to 1, initiates a non-maskable interrupt operation on
            this pBlade. When read, returns 0."

        ::=     { pBladeControlEntry 5 }


-- pBlade hardware monitors

pBladeHwMonitorTable OBJECT-TYPE
    SYNTAX      SEQUENCE OF PBladeMonitorEntry
    MAX-ACCESS  not-accessible
    STATUS      current
    DESCRIPTION
            "A list of pBlade monitor entries for each pBlade in the PAN.
            Voltage is measured in Volts, Temperature in degrees Celcius,
            and fan speed in Revolutions Per Minute"

        ::=     { pBlades 3 }


pBladeMonitorEntry OBJECT-TYPE
    SYNTAX      PBladeMonitorEntry
    MAX-ACCESS  not-accessible
    STATUS      current
    DESCRIPTION
            "Attributes of a specific pBlade hardware monitor."


    INDEX       { bladeFrameIndex, pBladeIndex, pBladeHwMonitorIndex }
        ::=     { pBladeHwMonitorTable 1 }


PBladeMonitorEntry ::=
    SEQUENCE {
        pBladeHwMonitorIndex
            Integer32,
        pBladeHwMonitorName
            DisplayString,
        pBladeHwMonitorType
            HardwareMonitorType,
        pBladeHwMonitorValue
            Integer32,
        pBladeHwMonitorValueDenomonator
            Integer32,
        pBladeHwMonitorUnits
            DisplayString
    }


pBladeHwMonitorIndex OBJECT-TYPE
    SYNTAX      Integer32 (1..2147483647)
    MAX-ACCESS  read-only
    STATUS      current
    DESCRIPTION
            "An integer value uniquely identifying the monitor within the
            pBlade."

        ::=     { pBladeMonitorEntry 1 }


pBladeHwMonitorName OBJECT-TYPE
    SYNTAX      DisplayString
    MAX-ACCESS  read-only
    STATUS      current
    DESCRIPTION
            "An String identifying the name of the hardware monitor."

        ::=     { pBladeMonitorEntry 2 }


pBladeHwMonitorType OBJECT-TYPE
    SYNTAX      HardwareMonitorType
    MAX-ACCESS  read-only
    STATUS      current
    DESCRIPTION
            "An integer encoding of the monitor type; voltage, temperature, or
            fanspeed."

        ::=     { pBladeMonitorEntry 3 }


pBladeHwMonitorValue OBJECT-TYPE
    SYNTAX      Integer32
    MAX-ACCESS  read-only
    STATUS      current
    DESCRIPTION
            "The integer representation of the current hardware sensor value.
            Voltage values are multiplied by 100 and rounted to convert from
            float to integer.  Thus 0.530 => 53"

        ::=     { pBladeMonitorEntry 4 }


pBladeHwMonitorValueDenomonator OBJECT-TYPE
    SYNTAX      Integer32
    MAX-ACCESS  read-only
    STATUS      current
    DESCRIPTION
            "The integer representation of the denomonator required to convert
            the integer incoding of the sensor value to the float value.
            For voltage sensors, this value is 100, for all other sensors,
            this value is 1."

        ::=     { pBladeMonitorEntry 5 }


pBladeHwMonitorUnits OBJECT-TYPE
    SYNTAX      DisplayString
    MAX-ACCESS  read-only
    STATUS      current
    DESCRIPTION
            "Monitor units."

        ::=     { pBladeMonitorEntry 6 }



vBladeTable OBJECT-TYPE
    SYNTAX      SEQUENCE OF VBladeEntry
    MAX-ACCESS  not-accessible
    STATUS      current
    DESCRIPTION
            "A list of vBlade entries containing information
            for vBlades the Egenera PAN."

        ::=     { pBlades 4 }


vBladeEntry OBJECT-TYPE
    SYNTAX      VBladeEntry
    MAX-ACCESS  not-accessible
    STATUS      current
    DESCRIPTION
            "An vBlade entry contains information for Processing
            Blades in the Egenera PAN."

    INDEX       { bladeFrameIndex, pBladeIndex, vBladeIndex }
        ::=     { vBladeTable 1 }


VBladeEntry ::=
    SEQUENCE {
        vBladeIndex
            Integer32,
        vBladePBladeIndex
            Integer32,
        vBladeFrameIndex
            Integer32,
        vBladePServerIndex
            Integer32,
        vBladeLPanIndex
            Integer32,
        vBladeName
            DisplayString,
        vBladeBladeFrameName
            DisplayString,
        vBladePServerName
            DisplayString,
        vBladeLPanName
            DisplayString,
        vBladeDescription
            DisplayString,
        vBladeHostName
            DisplayString,
        vBladeNumCpus
            Integer32,
        vBladeCpuSpeed
            Integer32,
        vBladeCpuModel
            DisplayString,
        vBladeMemorySize
            Integer32,
        vBladeCache
            Integer32,
        vBladeArchitecture
            DisplayString,
        vBladeSerialNumber
            DisplayString,
        vBladePartNumber
            DisplayString,
        vBladePowerStatus
            PowerStatusType,
        vBladePowerSupply
            DisplayString,
        vBladeActiveStatus
            TruthValue,
        vBladeAllocationStatus
            TruthValue,
        vBladeHealthStatus
            HealthStatusType,
        vBladeInDebugger
            TruthValue,
        vBladeBootStatus
            DisplayString,
        vBladeUpTime
            TimeTicks,
        vBladePoolIndex
            Integer32
    }

vBladeIndex OBJECT-TYPE
    SYNTAX      Integer32 (1..2147483647)
    MAX-ACCESS  read-only
    STATUS      current
    DESCRIPTION
            "An integer value uniquely identifying the vBlade within
            the pBlade."

        ::=     { vBladeEntry 1 }

vBladePBladeIndex OBJECT-TYPE
    SYNTAX      Integer32 (1..2147483647)
    MAX-ACCESS  read-only
    STATUS      current
    DESCRIPTION
            "An integer value uniquely identifying the pBladeIndex value
            of the pBlade hosting this vBlade.  The pBladeIndex is the
            slot of the pBlade."

        ::=     { vBladeEntry 2 }


vBladeFrameIndex OBJECT-TYPE
    SYNTAX      Integer32 (1..2147483647)
    MAX-ACCESS  read-only
    STATUS      current
    DESCRIPTION
            "An integer value identifying the bladeFrameIndex value of the
            BladeFrame that hosts this vBlade."

        ::=     { vBladeEntry 3 }


vBladePServerIndex OBJECT-TYPE
    SYNTAX      Integer32 (1..2147483647)
    MAX-ACCESS  read-only
    STATUS      current
    DESCRIPTION
            "An integer value identifying the pServerIndex of the pServer
            running on this vBlade, or -1 if the vBlade is not occupied
            by a pServer."

        ::=     { vBladeEntry 4 }


vBladeLPanIndex OBJECT-TYPE
    SYNTAX      Integer32 (1..2147483647)
    MAX-ACCESS  read-only
    STATUS      current
    DESCRIPTION
            "An integer value identifying the lPanIndex of the LPAN
            containing the pServer running on this vBlade, or -1 if the
            vBlade is not occupied by a pServer."

        ::=     { vBladeEntry 5 }


vBladeName OBJECT-TYPE
    SYNTAX      DisplayString
    MAX-ACCESS  read-only
    STATUS      current
    DESCRIPTION
            "A textual string identifying this vBlade."

        ::=     { vBladeEntry 6 }


vBladeBladeFrameName OBJECT-TYPE
    SYNTAX      DisplayString
    MAX-ACCESS  read-only
    STATUS      current
    DESCRIPTION
            "A textual string identifying the BladeFrame containing this
            vBlade."

        ::=     { vBladeEntry 7 }


vBladePServerName OBJECT-TYPE
    SYNTAX      DisplayString
    MAX-ACCESS  read-only
    STATUS      current
    DESCRIPTION
            "A textual string identifying the pServer running on this vBlade."

        ::=     { vBladeEntry 8 }

vBladeLPanName OBJECT-TYPE
    SYNTAX      DisplayString
    MAX-ACCESS  read-only
    STATUS      current
    DESCRIPTION
            "A textual string identifying the LPAN containing the pServer
            running on this vBlade."

        ::=     { vBladeEntry 9 }


vBladeDescription OBJECT-TYPE
    SYNTAX      DisplayString
    MAX-ACCESS  read-only
    STATUS      current
    DESCRIPTION
            "A textual string describing this vBlade."

        ::=     { vBladeEntry 10 }


vBladeHostName OBJECT-TYPE
    SYNTAX      DisplayString
    MAX-ACCESS  read-only
    STATUS      current
    DESCRIPTION
            "The hostname of the PServer running on this vBlade."

        ::=     { vBladeEntry 11 }


vBladeNumCpus OBJECT-TYPE
    SYNTAX      Integer32
    MAX-ACCESS  read-only
    STATUS      current
    DESCRIPTION
            "The number of CPUs on the vBlade."

        ::=     { vBladeEntry 12 }


vBladeCpuSpeed OBJECT-TYPE
    SYNTAX      Integer32
    MAX-ACCESS  read-only
    STATUS      current
    DESCRIPTION
            "The speed of the CPUs on the vBlade in Mhz."

        ::=     { vBladeEntry 13 }


vBladeCpuModel OBJECT-TYPE
    SYNTAX      DisplayString
    MAX-ACCESS  read-only
    STATUS      current
    DESCRIPTION
            "A textual string representing the CPU model this vBlade."

        ::=     { vBladeEntry 14 }


vBladeMemorySize OBJECT-TYPE
    SYNTAX      Integer32
    MAX-ACCESS  read-only
    STATUS      current
    DESCRIPTION
            "The size of the physical RAM installed on the vBlade,
            in MB."

        ::=     { vBladeEntry 15 }


vBladeCache OBJECT-TYPE
    SYNTAX      Integer32
    MAX-ACCESS  read-only
    STATUS      current
    DESCRIPTION
            "The size of the CPU cache installed on the vBlade,
            in kB."

        ::=     { vBladeEntry 16 }


vBladeArchitecture OBJECT-TYPE
    SYNTAX      DisplayString
    MAX-ACCESS  read-only
    STATUS      current
    DESCRIPTION
            "Describes the vBlade hardware architecture."

        ::=     { vBladeEntry 17 }


vBladeSerialNumber OBJECT-TYPE
    SYNTAX      DisplayString
    MAX-ACCESS  read-only
    STATUS      current
    DESCRIPTION
            "Describes the serial number of this vBlade."

        ::=     { vBladeEntry 18 }


vBladePartNumber OBJECT-TYPE
    SYNTAX      DisplayString
    MAX-ACCESS  read-only
    STATUS      current
    DESCRIPTION
            "Describes the part number of this vBlade."

        ::=     { vBladeEntry 19 }


vBladePowerStatus OBJECT-TYPE
    SYNTAX      PowerStatusType
    MAX-ACCESS  read-only
    STATUS      current
    DESCRIPTION
            "The power status of the vBlade."

        ::=     { vBladeEntry 20 }


vBladePowerSupply OBJECT-TYPE
    SYNTAX      DisplayString
    MAX-ACCESS  read-only
    STATUS      current
    DESCRIPTION
            "The name of the power supply used by this vBlade."

        ::=     { vBladeEntry 21 }


vBladeActiveStatus OBJECT-TYPE
    SYNTAX      TruthValue
    MAX-ACCESS  read-only
    STATUS      current
    DESCRIPTION
            "Indicates whether or not the blade is active."

        ::=     { vBladeEntry 22 }


vBladeAllocationStatus OBJECT-TYPE
    SYNTAX      TruthValue
    MAX-ACCESS  read-only
    STATUS      current
    DESCRIPTION
            "Indicates whether or not the blade is allocated."

        ::=     { vBladeEntry 23 }


vBladeHealthStatus OBJECT-TYPE
    SYNTAX      HealthStatusType
    MAX-ACCESS  read-only
    STATUS      current
    DESCRIPTION
            "An indication of the health of the BladeFrame."

        ::=     { vBladeEntry 24 }


vBladeInDebugger OBJECT-TYPE
    SYNTAX      TruthValue
    MAX-ACCESS  read-only
    STATUS      current
    DESCRIPTION
            "Indicates whether or not the kernel kernel on the vBlade has
            entered the debugger."

        ::=     { vBladeEntry 25 }


vBladeBootStatus OBJECT-TYPE
    SYNTAX      DisplayString
    MAX-ACCESS  read-only
    STATUS      current
    DESCRIPTION
            "Indicates the boot status of this vBlade."

        ::=     { vBladeEntry 26 }


vBladeUpTime OBJECT-TYPE
    SYNTAX      TimeTicks
    MAX-ACCESS  read-only
    STATUS      current
    DESCRIPTION
            "The amount of time that the BladeFrame has been up."

        ::=     { vBladeEntry 27 }


vBladePoolIndex OBJECT-TYPE
    SYNTAX      Integer32 (1..2147483647)
    MAX-ACCESS  read-only
    STATUS      current
    DESCRIPTION
            "An integer value identifying the poolindex of the pool containing
             the vBlade ."

        ::=     { vBladeEntry 28 }


-- vBlade controls

vBladeControlTable OBJECT-TYPE
    SYNTAX      SEQUENCE OF VBladeControlEntry
    MAX-ACCESS  not-accessible
    STATUS      current
    DESCRIPTION
            "A list of vBlade entries containing controls for
            vBlades in the Egenera PAN."

        ::=     { pBlades 5 }

vBladeControlEntry OBJECT-TYPE
    SYNTAX      VBladeControlEntry
    MAX-ACCESS  not-accessible
    STATUS      current
    DESCRIPTION
            "An vBlade entry contains controls for Processing
            Blades in the Egenera PAN."


    INDEX       { bladeFrameIndex, vBladeIndex }
    ::=     { vBladeControlTable 1 }

VBladeControlEntry ::=
    SEQUENCE {
        vBladeControlBoot
            Integer32,
        vBladeControlShutdown
            Integer32,
        vBladeControlReboot
            Integer32,
        vBladeControlNmi
            Integer32
}


vBladeControlBoot OBJECT-TYPE
    SYNTAX      Integer32
    MAX-ACCESS  read-write
    STATUS      current
    DESCRIPTION
            "When set to 1, initiates a boot operation on this Processing
            Blade. When read, returns 0."

    ::=     { vBladeControlEntry 1 }


vBladeControlShutdown OBJECT-TYPE
    SYNTAX      Integer32
    MAX-ACCESS  read-write
    STATUS      current
    DESCRIPTION
            "When set to 1, initiates a shutdown operation on this
            vBlade. When read, returns 0."

    ::=     { vBladeControlEntry 2 }


vBladeControlReboot OBJECT-TYPE
    SYNTAX      Integer32
    MAX-ACCESS  read-write
    STATUS      current
    DESCRIPTION
            "When set to 1, initiates a reboot operation on this
            vBlade. When read, returns 0."

    ::=     { vBladeControlEntry 3 }


vBladeControlNmi OBJECT-TYPE
    SYNTAX      Integer32
    MAX-ACCESS  read-write
    STATUS      current
    DESCRIPTION
            "When set to 1, initiates a non-maskable interrupt operation on
            this vBlade. When read, returns 0.  NMI is currently not supported,
            this is a no op."

    ::=     { vBladeControlEntry 4 }


-- pims group

pims OBJECT IDENTIFIER ::= { blades 4 }

-- PIM table
-- The PIM table contains information about PIMs in
-- BladeFrames.

pimTable OBJECT-TYPE
    SYNTAX      SEQUENCE OF PIMEntry
    MAX-ACCESS  not-accessible
    STATUS      current
    DESCRIPTION
            "A list of PIM entries containing information
            for PIMs the Egenera PAN."

        ::=     { pims 1 }


pimEntry OBJECT-TYPE
    SYNTAX      PIMEntry
    MAX-ACCESS  not-accessible
    STATUS      current
    DESCRIPTION
            "An PIM entry contains information for PIMs in the Egenera PAN."

    INDEX       { bladeFrameIndex, pimIndex }
        ::=     { pimTable 1 }


PIMEntry ::=
    SEQUENCE {
        pimIndex
            Integer32,
        pimFrameIndex
            Integer32,
        pimName
            DisplayString,
        pimBladeFrameName
            DisplayString,
        pimSerialNumber
            DisplayString,
        pimPartNumber
            DisplayString,
        pimFirmWare
            DisplayString,
        pimSelectedPower
            DisplayString,
        pimOutputPower
            Integer32,
        pimOutputCurrent
            Integer32,
        pimPreferredPower
            DisplayString,
        pimManualPowerPreference
            TruthValue,
        pimCurrentLimit
            Integer32,
        pimPowerLimit
            Integer32,
        pimInputVoltageA
            DisplayString,
        pimInputVoltageB
            DisplayString,
        pimInputFreq
            Integer32,
        pimVoltageFailoverTriggerRange
            Integer32,
        pimSelectedStatus
            TruthValue
    }


pimIndex OBJECT-TYPE
    SYNTAX      Integer32 (1..2147483647)
    MAX-ACCESS  read-only
    STATUS      current
    DESCRIPTION
            "An integer value uniquely identifying the PIM within
            the BladeFrame.  This corresponds to the physical location of the
            PIM within the BladeFrame."

        ::=     { pimEntry 1 }


pimFrameIndex OBJECT-TYPE
    SYNTAX      Integer32 (1..2147483647)
    MAX-ACCESS  read-only
    STATUS      current
    DESCRIPTION
            "An integer value identifying the bladeFrameIndex value of the
            BladeFrame that hosts this PIM."

        ::=     { pimEntry 2 }


pimName OBJECT-TYPE
    SYNTAX      DisplayString
    MAX-ACCESS  read-only
    STATUS      current
    DESCRIPTION
            "A textual string identifying this PIM."

        ::=     { pimEntry 3 }


pimBladeFrameName OBJECT-TYPE
    SYNTAX      DisplayString
    MAX-ACCESS  read-only
    STATUS      current
    DESCRIPTION
            "A textual string identifying the BladeFrame containing this
            PIM."

        ::=     { pimEntry 4 }


pimSerialNumber OBJECT-TYPE
    SYNTAX      DisplayString
    MAX-ACCESS  read-only
    STATUS      current
    DESCRIPTION
            "Describes the serial number of this PIM."

        ::=     { pimEntry 5 }


pimPartNumber OBJECT-TYPE
    SYNTAX      DisplayString
    MAX-ACCESS  read-only
    STATUS      current
    DESCRIPTION
            "Describes the part number of this PIM."

        ::=     { pimEntry 6 }


pimFirmWare OBJECT-TYPE
    SYNTAX      DisplayString
    MAX-ACCESS  read-only
    STATUS      current
    DESCRIPTION
            "The firmware of the PIM."

        ::=     { pimEntry 7 }


pimSelectedPower OBJECT-TYPE
    SYNTAX      DisplayString
    MAX-ACCESS  read-only
    STATUS      current
    DESCRIPTION
            "The selected power of the PIM."

        ::=     { pimEntry 8 }


pimOutputPower OBJECT-TYPE
    SYNTAX       Integer32 (1..2147483647)
    MAX-ACCESS   read-only
    STATUS       current
    DESCRIPTION
            "The output power of the PIM."

        ::=     { pimEntry 9 }


pimOutputCurrent OBJECT-TYPE
    SYNTAX       Integer32 (1..2147483647)
    MAX-ACCESS   read-only
    STATUS       current
    DESCRIPTION
            "The outpur current of the PIM."

        ::=     { pimEntry 10 }


pimPreferredPower OBJECT-TYPE
    SYNTAX      DisplayString
    MAX-ACCESS  read-only
    STATUS      current
    DESCRIPTION
            "The preferred power of the PIM."

        ::=     { pimEntry 11 }


pimManualPowerPreference OBJECT-TYPE
    SYNTAX      TruthValue
    MAX-ACCESS  read-only
    STATUS      current
    DESCRIPTION
            "The manual power preference of the PIM."

        ::=     { pimEntry 12 }


pimCurrentLimit OBJECT-TYPE
    SYNTAX       Integer32 (1..2147483647)
    MAX-ACCESS   read-only
    STATUS       current
    DESCRIPTION
            "The current limit of the PIM."

        ::=     { pimEntry 13 }


pimPowerLimit OBJECT-TYPE
    SYNTAX       Integer32 (1..2147483647)
    MAX-ACCESS   read-only
    STATUS       current
    DESCRIPTION
            "The power limit of the PIM."

        ::=     { pimEntry 14 }


pimInputVoltageA OBJECT-TYPE
    SYNTAX      DisplayString
    MAX-ACCESS  read-only
    STATUS      current
    DESCRIPTION
            "The input voltage A of the PIM."

        ::=     { pimEntry 15 }

pimInputVoltageB OBJECT-TYPE
    SYNTAX      DisplayString
    MAX-ACCESS  read-only
    STATUS      current
    DESCRIPTION
            "The InputVoltageB of the PIM."

        ::=     { pimEntry 16 }

pimInputFreq OBJECT-TYPE
    SYNTAX       Integer32 (1..2147483647)
    MAX-ACCESS   read-only
    STATUS       current
    DESCRIPTION
            "The input frequency of the PIM."

        ::=     { pimEntry 17 }

pimVoltageFailoverTriggerRange OBJECT-TYPE
    SYNTAX       Integer32 (1..2147483647)
    MAX-ACCESS   read-only
    STATUS       current
    DESCRIPTION
            "This attribute is deprecated.  The trigger value
            is fixed at 85% of PIM maximum voltage"

        ::=     { pimEntry 18 }


pimSelectedStatus OBJECT-TYPE
    SYNTAX      TruthValue
    MAX-ACCESS  read-only
    STATUS      current
    DESCRIPTION
            "Indicates whether or not the PIM is selected."

        ::=     { pimEntry 19 }


chassisTable OBJECT-TYPE
    SYNTAX      SEQUENCE OF ChassisEntry
    MAX-ACCESS  not-accessible
    STATUS      current
    DESCRIPTION
            "A list of Chassis entries describing attributes of non-egenera
            hardware chassis contained in the PAN.  This is a sparse table."

        ::=     { bladeFrames 4 }


chassisEntry OBJECT-TYPE
    SYNTAX      ChassisEntry
    MAX-ACCESS  not-accessible
    STATUS      current
    DESCRIPTION
            "A Chassis entry contains general information about each
            Chassis in the Egenera PAN."

    INDEX       { bladeFrameIndex, chassisIndex }
        ::=     { chassisTable 1 }


ChassisEntry ::=
    SEQUENCE {
        chassisIndex
            Integer32,
        chassisBladeFrameIndex
            Integer32,
        chassisName
            DisplayString,
        chassisType
            DisplayString,
        chassisManagementIp
            IpAddress
    }

-- other attributes may be added in the future as needed

chassisIndex OBJECT-TYPE
    SYNTAX      Integer32 (1..2147483647)
    MAX-ACCESS  read-only
    STATUS      current
    DESCRIPTION
            "An integer value uniquely identifying the hardware chassis."

        ::=     { chassisEntry 1 }


chassisBladeFrameIndex OBJECT-TYPE
    SYNTAX      Integer32 (1..2147483647)
    MAX-ACCESS  read-only
    STATUS      current
    DESCRIPTION
            "An integer value identifying the bladeFrameIndex value of the
            BladeFrame that this chassis contributes to."

        ::=     { chassisEntry 2 }


chassisName OBJECT-TYPE
    SYNTAX      DisplayString
    MAX-ACCESS  read-only
    STATUS      current
    DESCRIPTION
            "A textual string identifying the chassis."

        ::=     { chassisEntry 3 }


chassisType OBJECT-TYPE
    SYNTAX      DisplayString
    MAX-ACCESS  read-only
    STATUS      current
    DESCRIPTION
            "A textual string identifying the type chassis."

        ::=     { chassisEntry 4 }


chassisManagementIp OBJECT-TYPE
    SYNTAX      IpAddress
    MAX-ACCESS  read-only
    STATUS      current
    DESCRIPTION
            "The management IP address of the chassis."

        ::=     { chassisEntry 5 }




devices   OBJECT IDENTIFIER ::= { management 3 }

-- cBlade CD-ROMs connected to the PAN

cdroms    OBJECT IDENTIFIER ::= { devices 1 }


cdromTable   OBJECT-TYPE
    SYNTAX      SEQUENCE OF CDRomEntry
    MAX-ACCESS  not-accessible
    STATUS      current
    DESCRIPTION
            "A list of cdrom entries containing information about each
            cdrom allocated to this LPAN."

        ::=     { cdroms 1 }


cdromEntry OBJECT-TYPE
    SYNTAX      CDRomEntry
    MAX-ACCESS  not-accessible
    STATUS      current
    DESCRIPTION
            "Information specific to each cdrom in the PAN, or allocated to
            the LPAN if LPAN agent."

    INDEX       { cdromBladeFrameIndex, cdromCBladeIndex,
                  IMPLIED cdromIdOctets }
        ::=     { cdromTable 1 }

CDRomEntry ::=
    SEQUENCE {
        cdromIdOctets
            OCTET STRING,
        cdromCBladeIndex
            Integer32,
        cdromBladeFrameIndex
            Integer32,
        cdromId
            DisplayString,
        cdromLPANIndex
            Integer32,
        cdromMajor
            Integer32,
        cdromMinor
            Integer32,
        cdromVendor
            DisplayString,
        cdromModel
            DisplayString,
        cdromSerialNumber
            DisplayString,
        cdromRev
            DisplayString,
        cdromEnabled
            TruthValue,
        cdromCapacity
            Integer32
    }


cdromIdOctets OBJECT-TYPE
    SYNTAX      OCTET STRING (SIZE(4))
    MAX-ACCESS  read-only
    STATUS      current
    DESCRIPTION
            "A sequence of 4 bytes encoding the values of HBA number,
            BUS ID, target device ID and LUN."

        ::=     { cdromEntry 1 }

cdromCBladeIndex OBJECT-TYPE
    SYNTAX      Integer32 (1..2147483647)
    MAX-ACCESS  read-only
    STATUS      current
    DESCRIPTION
            "The cBladeIndex value of the cBlade hosting this CD-Rom."

        ::=     { cdromEntry 2 }

cdromBladeFrameIndex OBJECT-TYPE
    SYNTAX      Integer32 (1..2147483647)
    MAX-ACCESS  read-only
    STATUS      current
    DESCRIPTION
            "The bladeFrameIndex value of the BladeFrame hosting this CD-Rom."

        ::=     { cdromEntry 3 }

cdromId OBJECT-TYPE
    SYNTAX      DisplayString
    MAX-ACCESS  read-only
    STATUS      current
    DESCRIPTION
            "A human readable string consisting of dot separated values
            of HBA number, BUS ID, target device ID and LUN."

        ::=     { cdromEntry 4 }

cdromLPANIndex OBJECT-TYPE
    SYNTAX      Integer32
    MAX-ACCESS  read-only
    STATUS      current
    DESCRIPTION
            "The lpanIndex value of the LPAN this cdrom is allocated to, or
            0 if not allocated."

        ::=     { cdromEntry 5}


cdromMajor OBJECT-TYPE
    SYNTAX      Integer32
    MAX-ACCESS  read-only
    STATUS      current
    DESCRIPTION
            "The minor number of this CD-Rom device."

        ::=     { cdromEntry 6 }


cdromMinor OBJECT-TYPE
    SYNTAX      Integer32
    MAX-ACCESS  read-only
    STATUS      current
    DESCRIPTION
            "The minor number of this CD-Rom device."

        ::=     { cdromEntry 7 }


cdromVendor OBJECT-TYPE
    SYNTAX      DisplayString
    MAX-ACCESS  read-only
    STATUS      current
    DESCRIPTION
            "A textual string identifying the cdrom vendor."

        ::=     { cdromEntry 8 }


cdromModel OBJECT-TYPE
    SYNTAX      DisplayString
    MAX-ACCESS  read-only
    STATUS      current
    DESCRIPTION
            "A textual string identifying the cdrom model."

        ::=     { cdromEntry 9 }


cdromSerialNumber OBJECT-TYPE
    SYNTAX      DisplayString
    MAX-ACCESS  read-only
    STATUS      current
    DESCRIPTION
            "A textual string providing the serial number of the cdrom."

        ::=     { cdromEntry 10 }


cdromRev OBJECT-TYPE
    SYNTAX      DisplayString
    MAX-ACCESS  read-only
    STATUS      current
    DESCRIPTION
            "The firmare revision used by this CD-ROM."

        ::=     { cdromEntry 11 }


cdromEnabled OBJECT-TYPE
    SYNTAX      TruthValue
    MAX-ACCESS  read-only
    STATUS      current
    DESCRIPTION
            "Indicates wether the cdrom is enabled (true), or disabled
            (false)."

        ::=     { cdromEntry 12 }


cdromCapacity OBJECT-TYPE
    SYNTAX      Integer32
    MAX-ACCESS  read-only
    STATUS      current
    DESCRIPTION
            "The storage capacity of the cdrom in megabytes."

        ::=     { cdromEntry 13 }



-- CD-ROM LPAN allocations

cdromLPanAllocTable  OBJECT-TYPE
    SYNTAX      SEQUENCE OF CDRomLPanAllocEntry
    MAX-ACCESS  not-accessible
    STATUS      current
    DESCRIPTION
            "A list of LPAN indicies identifying LPAN cdrom allocations."

        ::=     { cdroms 2 }


cdromLPanAllocEntry OBJECT-TYPE
    SYNTAX      CDRomLPanAllocEntry
    MAX-ACCESS  not-accessible
    STATUS      current
    DESCRIPTION
            "Information specific to each pServer cdrom allocation."

    INDEX       { lPanIndex, cdromBladeFrameIndex,
                  cdromCBladeIndex, IMPLIED cdromIdOctets }
        ::=     { cdromLPanAllocTable 1 }


CDRomLPanAllocEntry ::=
    SEQUENCE {
        cdromLPanAllocIdOctets
            OCTET STRING,
        cdromLPanAllocBladeFrameIndex
            Integer32,
        cdromLPanAllocCBladeIndex
            Integer32,
        cdromLPanAllocLPanIndex
            Integer32,
        cdromLPanAllocEnabled
            TruthValue
    }


cdromLPanAllocIdOctets OBJECT-TYPE
    SYNTAX      OCTET STRING (SIZE(4))
    MAX-ACCESS  read-only
    STATUS      current
    DESCRIPTION
            "A sequence of 4 bytes encoding the values of HBA number,
            BUS ID, target device ID and LUN of the cdrom."

        ::=     { cdromLPanAllocEntry 1 }


cdromLPanAllocBladeFrameIndex OBJECT-TYPE
    SYNTAX      Integer32
    MAX-ACCESS  read-only
    STATUS      current
    DESCRIPTION
            "The bladeFrameIndex value of the BladeFrame hosting this
            CD-ROM."

        ::=     { cdromLPanAllocEntry 2 }

cdromLPanAllocCBladeIndex OBJECT-TYPE
    SYNTAX      Integer32
    MAX-ACCESS  read-only
    STATUS      current
    DESCRIPTION
            "The cBladeIndex value of the cBlade hosting this
            CD-ROM."

        ::=     { cdromLPanAllocEntry 3 }


cdromLPanAllocLPanIndex OBJECT-TYPE
    SYNTAX      Integer32
    MAX-ACCESS  read-only
    STATUS      current
    DESCRIPTION
            "The lpanIndex of the LPAN hosting the LPAN this cdrom is
            allocated to."

        ::=     { cdromLPanAllocEntry 4 }


cdromLPanAllocEnabled OBJECT-TYPE
    SYNTAX      TruthValue
    MAX-ACCESS  read-only
    STATUS      current
    DESCRIPTION
            "Indicates whether the LPAN cdrom mapping is currently
            enabled."

        ::=     { cdromLPanAllocEntry 5 }



cdromPSvrAllocTable   OBJECT-TYPE
    SYNTAX      SEQUENCE OF CDRomPSvrAllocEntry
    MAX-ACCESS  not-accessible
    STATUS      current
    DESCRIPTION
            "A list of LPAN, pServer index pairs identifying pServer cdrom
            allocations."

        ::=     { cdroms 3 }


cdromPSvrAllocEntry OBJECT-TYPE
    SYNTAX      CDRomPSvrAllocEntry
    MAX-ACCESS  not-accessible
    STATUS      current
    DESCRIPTION
            "Information specific to each pServer cdrom allocation."

    INDEX       { lPanIndex, pServerIndex, bladeFrameIndex, cBladeIndex,
                  IMPLIED cdromIdOctets }

        ::=     { cdromPSvrAllocTable 1 }

CDRomPSvrAllocEntry ::=
    SEQUENCE {
        cdromPSvrAllocIdOctets
            OCTET STRING,
        cdromPSvrAllocCBladeIndex
            Integer32,
        cdromPSvrAllocBladeFrameIndex
            Integer32,
        cdromPSvrAllocpSvrIndex
            Integer32,
        cdromPSvrAllocLPanIndex
            Integer32
    }



cdromPSvrAllocIdOctets OBJECT-TYPE
    SYNTAX      OCTET STRING (SIZE(4))
    MAX-ACCESS  read-only
    STATUS      current
    DESCRIPTION
            "A sequence of 4 bytes encoding the values of HBA number,
            BUS ID, target device ID and LUN of the cdrom."

        ::=     { cdromPSvrAllocEntry 1 }


cdromPSvrAllocBladeFrameIndex OBJECT-TYPE
    SYNTAX      Integer32
    MAX-ACCESS  read-only
    STATUS      current
    DESCRIPTION
            "The bladeFrameIndex value of the BladeFrame hosting this
            CD-ROM."

        ::=     { cdromPSvrAllocEntry 2 }

cdromPSvrAllocCBladeIndex OBJECT-TYPE
    SYNTAX      Integer32
    MAX-ACCESS  read-only
    STATUS      current
    DESCRIPTION
            "The cBladeIndex value of the cBlade hosting this
            CD-ROM."

        ::=     { cdromPSvrAllocEntry 3 }


cdromPSvrAllocLPanIndex OBJECT-TYPE
    SYNTAX      Integer32
    MAX-ACCESS  read-only
    STATUS      current
    DESCRIPTION
            "The lpanIndex of the LPAN hosting the pServer this cdrom is
            allocated to."

        ::=     { cdromPSvrAllocEntry 4 }

cdromPSvrAllocpSvrIndex OBJECT-TYPE
    SYNTAX      Integer32
    MAX-ACCESS  read-only
    STATUS      current
    DESCRIPTION
            "The lpanIndex of the pServer hosting the pServer this cdrom is
            allocated to."

        ::=     { cdromPSvrAllocEntry 5 }



-- disks connected to the PAN

disks     OBJECT IDENTIFIER ::= { devices 2 }

diskTable   OBJECT-TYPE
    SYNTAX      SEQUENCE OF DiskEntry
    MAX-ACCESS  not-accessible
    STATUS      current
    DESCRIPTION
            "A list of disk entries containing information about each
            disk allocated to this LPAN."

        ::=     { disks 1 }


diskEntry OBJECT-TYPE
    SYNTAX      DiskEntry
    MAX-ACCESS  not-accessible
    STATUS      current
    DESCRIPTION
            "Information specific to each disk in the PAN, or allocated to
            the LPAN if LPAN agent."

    INDEX       { IMPLIED diskIdOctets }
        ::=     { diskTable 1 }

DiskEntry ::=
    SEQUENCE {
        diskIdOctets
            OCTET STRING,
        diskId
            DisplayString,
        diskMajor
            Integer32,
        diskMinor
            Integer32,
        diskVendor
            DisplayString,
        diskModel
            DisplayString,
        diskSerialNumber
            DisplayString,
        diskRev
            DisplayString,
        diskEnabled
            TruthValue,
        diskCapacity
            Integer32,
        diskDescription
            DisplayString
    }


diskIdOctets OBJECT-TYPE
    SYNTAX      OCTET STRING (SIZE(4))
    MAX-ACCESS  read-only
    STATUS      current
    DESCRIPTION
            "A sequence of 4 bytes encoding the values of HBA number,
            BUS ID, target device ID and LUN."

        ::=     { diskEntry 1}


diskId OBJECT-TYPE
    SYNTAX      DisplayString
    MAX-ACCESS  read-only
    STATUS      current
    DESCRIPTION
            "A human readable string consisting of dot separated values
            of HBA number, BUS ID, target device ID and LUN."

        ::=     { diskEntry 2}


diskMajor OBJECT-TYPE
    SYNTAX      Integer32
    MAX-ACCESS  read-only
    STATUS      current
    DESCRIPTION
            "The major number of this disk device.  This object is deprectated
            and will be removed in future releases"

        ::=     { diskEntry 3 }


diskMinor OBJECT-TYPE
    SYNTAX      Integer32
    MAX-ACCESS  read-only
    STATUS      current
    DESCRIPTION
            "The minor number of this disk device.  This object is deprecated
            and will be removed in future releases"

        ::=     { diskEntry 4 }


diskVendor OBJECT-TYPE
    SYNTAX      DisplayString
    MAX-ACCESS  read-only
    STATUS      current
    DESCRIPTION
            "A textual string identifying the disk vendor."

        ::=     { diskEntry 5 }


diskModel OBJECT-TYPE
    SYNTAX      DisplayString
    MAX-ACCESS  read-only
    STATUS      current
    DESCRIPTION
            "A textual string identifying the disk model."

        ::=     { diskEntry 6 }


diskSerialNumber OBJECT-TYPE
    SYNTAX      DisplayString
    MAX-ACCESS  read-only
    STATUS      current
    DESCRIPTION
            "A textual string providing the serial number of the disk"

        ::=     { diskEntry 7 }


diskRev OBJECT-TYPE
    SYNTAX      DisplayString
    MAX-ACCESS  read-only
    STATUS      current
    DESCRIPTION
            "The firmare revision used by this disk."

        ::=     { diskEntry 8 }


diskEnabled OBJECT-TYPE
    SYNTAX      TruthValue
    MAX-ACCESS  read-only
    STATUS      current
    DESCRIPTION
            "Indicates wether the disk is enabled (true), or disabled
            (false)."

        ::=     { diskEntry 9 }


diskCapacity OBJECT-TYPE
    SYNTAX      Integer32
    MAX-ACCESS  read-only
    STATUS      current
    DESCRIPTION
            "The storage capacity of the disk in megabytes."

        ::=     { diskEntry 10 }


diskDescription OBJECT-TYPE
    SYNTAX      DisplayString
    MAX-ACCESS  read-only
    STATUS      current
    DESCRIPTION
            "Disk description string."

        ::=     { diskEntry 11 }


-- LPAN disk allocations

diskLPanAllocTable  OBJECT-TYPE
    SYNTAX      SEQUENCE OF DiskLPanAllocEntry
    MAX-ACCESS  not-accessible
    STATUS      current
    DESCRIPTION
            "A list of LPAN indicies identifying LPAN disk allocations."

        ::=     { disks 2 }


diskLPanAllocEntry OBJECT-TYPE
    SYNTAX      DiskLPanAllocEntry
    MAX-ACCESS  not-accessible
    STATUS      current
    DESCRIPTION
            "Information specific to each LPAN disk allocation."

    INDEX       { lPanIndex, IMPLIED diskIdOctets }
        ::=     { diskLPanAllocTable 1 }


DiskLPanAllocEntry ::=
    SEQUENCE {
        diskLPanAllocIdOctets
            OCTET STRING,
        diskLPanAllocLPanIndex
            Integer32,
        diskLPanAllocEnabled
            TruthValue
    }


diskLPanAllocIdOctets OBJECT-TYPE
    SYNTAX      OCTET STRING (SIZE(4))
    MAX-ACCESS  read-only
    STATUS      current
    DESCRIPTION
            "A sequence of 4 bytes encoding the values of HBA number,
            BUS ID, target device ID and LUN of the disk."

        ::=     { diskLPanAllocEntry 1 }


diskLPanAllocLPanIndex OBJECT-TYPE
    SYNTAX      Integer32
    MAX-ACCESS  read-only
    STATUS      current
    DESCRIPTION
            "The lpanIndex of the LPAN hosting the LPAN this disk is
            allocated to."

        ::=     { diskLPanAllocEntry 2 }

diskLPanAllocEnabled OBJECT-TYPE
    SYNTAX      TruthValue
    MAX-ACCESS  read-only
    STATUS      current
    DESCRIPTION
            "Indicates whether the disk is currently enabled within the LPAN."

        ::=     { diskLPanAllocEntry 3 }


-- pServer disk allocations

-- in this context, diskIdOctets is a 4 byte OCTET STRING encoding of
-- the disk's HBA number, BUS ID, target device ID, and LUN values.
--
-- diskNameOctets is the OCTET STRING encoding of the asscii codes
-- comprising the name of the device special file that the disk is
-- mapped to.

diskPSvrAllocTable   OBJECT-TYPE
    SYNTAX      SEQUENCE OF DiskPSvrAllocEntry
    MAX-ACCESS  not-accessible
    STATUS      current
    DESCRIPTION
            "A list of LPAN, pServer index pairs identifying pServer disk
            allocations."

        ::=     { disks 3 }


diskPSvrAllocEntry OBJECT-TYPE
    SYNTAX      DiskPSvrAllocEntry
    MAX-ACCESS  not-accessible
    STATUS      current
    DESCRIPTION
            "Information specific to each pServer disk allocation."

    INDEX       { lPanIndex, pServerIndex, IMPLIED diskIdOctets }
        ::=     { diskPSvrAllocTable 1 }

DiskPSvrAllocEntry ::=
    SEQUENCE {
        diskPSvrAllocIdOctets
            OCTET STRING,
        diskPSvrAllocPSvrIndex
            Integer32,
        diskPSvrAllocLPanIndex
            Integer32
    }



diskPSvrAllocIdOctets OBJECT-TYPE
    SYNTAX      OCTET STRING (SIZE(4))
    MAX-ACCESS  read-only
    STATUS      current
    DESCRIPTION
            "A sequence of 4 bytes encoding the values of HBA number,
            BUS ID, target device ID and LUN of the disk."

        ::=     { diskPSvrAllocEntry 1 }


diskPSvrAllocPSvrIndex OBJECT-TYPE
    SYNTAX      Integer32
    MAX-ACCESS  read-only
    STATUS      current
    DESCRIPTION
            "The lpanIndex of the pServer hosting the pServer this disk is
            allocated to."

        ::=     { diskPSvrAllocEntry 2 }


diskPSvrAllocLPanIndex OBJECT-TYPE
    SYNTAX      Integer32
    MAX-ACCESS  read-only
    STATUS      current
    DESCRIPTION
            "The lpanIndex of the LPAN hosting the pServer this disk is
            allocated to."

        ::=     { diskPSvrAllocEntry 3 }

-- tapes connected to the PAN
tapes OBJECT IDENTIFIER ::= { devices 5 }



tapeTable   OBJECT-TYPE
    SYNTAX      SEQUENCE OF TapeEntry
    MAX-ACCESS      not-accessible
    STATUS      current
    DESCRIPTION
            "A list of tape entries containing information about each
            tape allocated to this LPAN."

        ::=     { tapes 1 }


tapeEntry OBJECT-TYPE
    SYNTAX      TapeEntry
    MAX-ACCESS  not-accessible
    STATUS      current
    DESCRIPTION
            "Information specific to each tape in the PAN, or allocated to
            the LPAN if LPAN agent."

    INDEX       { IMPLIED tapeIdOctets }
        ::=     { tapeTable 1 }

TapeEntry ::=
    SEQUENCE {
        tapeIdOctets
            OCTET STRING,
        tapeId
            DisplayString,
        tapeMajor
            Integer32,
        tapeMinor
            Integer32,
        tapeVendor
            DisplayString,
        tapeModel
            DisplayString,
        tapeSerialNumber
            DisplayString,
        tapeRev
            DisplayString,
        tapeEnabled
            TruthValue
    }


tapeIdOctets OBJECT-TYPE
    SYNTAX      OCTET STRING (SIZE(4))
    MAX-ACCESS  read-only
    STATUS      current
    DESCRIPTION
            "A sequence of 4 bytes encoding the values of HBA number,
            BUS ID, target device ID and LUN."

        ::=     { tapeEntry 1}


tapeId OBJECT-TYPE
    SYNTAX      DisplayString
    MAX-ACCESS  read-only
    STATUS      current
    DESCRIPTION
            "A human readable string consisting of dot separated values
            of HBA number, BUS ID, target device ID and LUN."

        ::=     { tapeEntry 2}


tapeMajor OBJECT-TYPE
    SYNTAX      Integer32
    MAX-ACCESS  read-only
    STATUS      current
    DESCRIPTION
            "The major number of this tape device."

        ::=     { tapeEntry 3 }


tapeMinor OBJECT-TYPE
    SYNTAX      Integer32
    MAX-ACCESS  read-only
    STATUS      current
    DESCRIPTION
            "The minor number of this tape device."

        ::=     { tapeEntry 4 }


tapeVendor OBJECT-TYPE
    SYNTAX      DisplayString
    MAX-ACCESS  read-only
    STATUS      current
    DESCRIPTION
            "A textual string identifying the tape vendor."

        ::=     { tapeEntry 5 }


tapeModel OBJECT-TYPE
    SYNTAX      DisplayString
    MAX-ACCESS  read-only
    STATUS      current
    DESCRIPTION
            "A textual string identifying the tape model."

        ::=     { tapeEntry 6 }


tapeSerialNumber OBJECT-TYPE
    SYNTAX      DisplayString
    MAX-ACCESS  read-only
    STATUS      current
    DESCRIPTION
            "A textual string providing the serial number of the tape"

        ::=     { tapeEntry 7 }


tapeRev OBJECT-TYPE
    SYNTAX      DisplayString
    MAX-ACCESS  read-only
    STATUS      current
    DESCRIPTION
            "The firmare revision used by this tape."

        ::=     { tapeEntry 8 }


tapeEnabled OBJECT-TYPE
    SYNTAX      TruthValue
    MAX-ACCESS  read-only
    STATUS      current
    DESCRIPTION
            "Indicates wether the tape is enabled (true), or disabled
            (false)."

        ::=     { tapeEntry 9 }


-- LPAN tape allocations

tapeLPanAllocTable  OBJECT-TYPE
    SYNTAX      SEQUENCE OF TapeLPanAllocEntry
    MAX-ACCESS  not-accessible
    STATUS      current
    DESCRIPTION
            "A list of LPAN indicies identifying LPAN tape allocations."

        ::=     { tapes 2 }


tapeLPanAllocEntry OBJECT-TYPE
    SYNTAX      TapeLPanAllocEntry
    MAX-ACCESS  not-accessible
    STATUS      current
    DESCRIPTION
            "Information specific to each LPAN tape allocation."

    INDEX       { lPanIndex, IMPLIED tapeIdOctets }
        ::=     { tapeLPanAllocTable 1 }


TapeLPanAllocEntry ::=
    SEQUENCE {
        tapeLPanAllocIdOctets
            OCTET STRING,
        tapeLPanAllocLPanIndex
            Integer32,
        tapeLPanAllocEnabled
            TruthValue
    }


tapeLPanAllocIdOctets OBJECT-TYPE
    SYNTAX      OCTET STRING (SIZE(4))
    MAX-ACCESS  read-only
    STATUS      current
    DESCRIPTION
            "A sequence of 4 bytes encoding the values of HBA number,
            BUS ID, target device ID and LUN of the tape."

        ::=     { tapeLPanAllocEntry 1 }


tapeLPanAllocLPanIndex OBJECT-TYPE
    SYNTAX      Integer32
    MAX-ACCESS  read-only
    STATUS      current
    DESCRIPTION
            "The lpanIndex of the LPAN hosting the LPAN this tape is
            allocated to."

        ::=     { tapeLPanAllocEntry 2 }

tapeLPanAllocEnabled OBJECT-TYPE
    SYNTAX      TruthValue
    MAX-ACCESS  read-only
    STATUS      current
    DESCRIPTION
            "Indicates whether the tape is currently enabled within the LPAN."

        ::=     { tapeLPanAllocEntry 3 }


-- pServer tape allocations

-- in this context, tapeIdOctets is a 4 byte OCTET STRING encoding of
-- the tape's HBA number, BUS ID, target device ID, and LUN values.
--
-- tapeNameOctets is the OCTET STRING encoding of the asscii codes
-- comprising the name of the device special file that the tape is
-- mapped to.

tapePSvrAllocTable   OBJECT-TYPE
    SYNTAX      SEQUENCE OF TapePSvrAllocEntry
    MAX-ACCESS  not-accessible
    STATUS      current
    DESCRIPTION
            "A list of LPAN, pServer index pairs identifying pServer tape
            allocations."

        ::=     { tapes 3 }


tapePSvrAllocEntry OBJECT-TYPE
    SYNTAX      TapePSvrAllocEntry
    MAX-ACCESS  not-accessible
    STATUS      current
    DESCRIPTION
            "Information specific to each pServer tape allocation."

    INDEX       { lPanIndex, pServerIndex, IMPLIED tapeIdOctets }
        ::=     { tapePSvrAllocTable 1 }

TapePSvrAllocEntry ::=
    SEQUENCE {
        tapePSvrAllocIdOctets
            OCTET STRING,
        tapePSvrAllocPSvrIndex
            Integer32,
        tapePSvrAllocLPanIndex
            Integer32
    }



tapePSvrAllocIdOctets OBJECT-TYPE
    SYNTAX      OCTET STRING (SIZE(4))
    MAX-ACCESS  read-only
    STATUS      current
    DESCRIPTION
            "A sequence of 4 bytes encoding the values of HBA number,
            BUS ID, target device ID and LUN of the tape."

        ::=     { tapePSvrAllocEntry 1 }


tapePSvrAllocPSvrIndex OBJECT-TYPE
    SYNTAX      Integer32
    MAX-ACCESS  read-only
    STATUS      current
    DESCRIPTION
            "The lpanIndex of the pServer hosting the pServer this tape is
            allocated to."

        ::=     { tapePSvrAllocEntry 2 }


tapePSvrAllocLPanIndex OBJECT-TYPE
    SYNTAX      Integer32
    MAX-ACCESS  read-only
    STATUS      current
    DESCRIPTION
            "The lpanIndex of the LPAN hosting the pServer this tape is
            allocated to."

        ::=     { tapePSvrAllocEntry 3 }


rEths OBJECT IDENTIFIER ::= { devices 3 }

LoadBalanceType ::= TEXTUAL-CONVENTION
    STATUS      current
    DESCRIPTION
            "Describes the load balance policy in place."
    SYNTAX INTEGER {
        pair(1),        -- (default) packets are transmitted on the same cBlade
                        --      that is receiving packets.
        inverse(2),     -- packets are transmitted on the failover partner not currently
                        --      enabled
        balance(3),     -- packets are transmitted via either cBlade. With this option, a
                        --      pBlade attempts to load-balance between both cBlades.
                        --      NOTE: Certain external switches may not allow this
                        --              configuration.
        undefined(999)
}

REthStateType ::= TEXTUAL-CONVENTION
    STATUS      current
    DESCRIPTION
            "Describes the redundant ethernet state."
    SYNTAX INTEGER {
        redundant(1),       -- both eths are not failed
        not-redundant(2),   -- one of the two eths is known to be failed
        degraded(3),        -- one of the two eths is known to be failed,
                            -- and the other is unknown
        failed(4),          -- both eths are known to be failed
        unknown(999)
}


rEthTable   OBJECT-TYPE
    SYNTAX      SEQUENCE OF REthEntry
    MAX-ACCESS  not-accessible
    STATUS      current
    DESCRIPTION
            "A list of rEth entries containing information about each
            redundant Ethernet (rEth) in the PAN.  A rEth is a pair of
            Ethernet Network Interface Cards (NICs), one on each cBlade,
            with the same configuration and external connectivity.  A rEth
            provides  redundant load-balancing and failover capability for
            BladeFrame network connectivity.

           Egenera rEth Naming Conventions

           ethx@bladeframename/cn
                  Reference  to a cBlade Network Interface Card (NIC).
                  BladeFrame naming conventions require you to use a '/'
                  between the BladeFrame name and cBlade number. For example
                  eth1 on cBlade 2 on the BladeFrame named Egenera, would be
                  referred  to as 'eth1@Egenera/c2'."

        ::=     { rEths 1 }


rEthEntry OBJECT-TYPE
    SYNTAX      REthEntry
    MAX-ACCESS  not-accessible
    STATUS      current
    DESCRIPTION
            "Information specific to each rEth in the PAN."

    INDEX       { rEthIndex }
        ::=     { rEthTable 1 }

REthEntry ::=
    SEQUENCE {
        rEthIndex
            Integer32,
        rEthName
            DisplayString,
        rEthPrimaryEth
            DisplayString,
        rEthPrimaryEthIndexOid
            OBJECT IDENTIFIER,
        rEthInterface1
            DisplayString,
        rEthInterface1IndexOid
            OBJECT IDENTIFIER,
        rEthInterface2
            DisplayString,
        rEthInterface2IndexOid
            OBJECT IDENTIFIER,
        rEthMACAddressOctets
            PhysAddress,
        rEthMACAddressString
            DisplayString,
        rEthAutoMACAssign
            TruthValue,
        rEthFlowControlOn
            TruthValue,
        rEthLoadBalancePolicy
            LoadBalanceType,
        rEthState
            REthStateType,
        rEthFrameIndex
            Integer32,
        rEthMTUSize
            Integer32
    }

rEthIndex OBJECT-TYPE
    SYNTAX      Integer32 (1..2147483647)
    MAX-ACCESS  read-only
    STATUS      current
    DESCRIPTION
            "An integer value uniquely identifying the rEth within the PAN"

        ::=     { rEthEntry 1 }

rEthName OBJECT-TYPE
    SYNTAX      DisplayString
    MAX-ACCESS  read-only
    STATUS      current
    DESCRIPTION
            "A human readable string uniquely identifying the rEth."

        ::=     { rEthEntry 2 }


rEthPrimaryEth OBJECT-TYPE
    SYNTAX      DisplayString
    MAX-ACCESS  read-only
    STATUS      current
    DESCRIPTION
            "Identifies the primary Eth of the Reth."

        ::=     { rEthEntry 3 }


rEthPrimaryEthIndexOid OBJECT-TYPE
    SYNTAX      OBJECT IDENTIFIER
    MAX-ACCESS  read-only
    STATUS      current
    DESCRIPTION
            "An encoding of the cBlade Eth BladeFrameIndex, cBladeIndex, and
            cBladeEth index, uniquely identifying the cBlade Eth configured
            as the primary Eth."

        ::=     { rEthEntry 4 }


rEthInterface1 OBJECT-TYPE
    SYNTAX      DisplayString
    MAX-ACCESS  read-only
    STATUS      current
    DESCRIPTION
            "Specifies the first cBlade NIC of a rEth."

        ::=     { rEthEntry 5 }


rEthInterface1IndexOid OBJECT-TYPE
    SYNTAX      OBJECT IDENTIFIER
    MAX-ACCESS  read-only
    STATUS      current
    DESCRIPTION
            "An encoding of the cBlade Eth BladeFrameIndex, cBladeIndex, and
            cBladeEth index, uniquely identifying the cBlade Eth configured
            as 'interface1'."

        ::=     { rEthEntry 6 }


rEthInterface2 OBJECT-TYPE
    SYNTAX      DisplayString
    MAX-ACCESS  read-only
    STATUS      current
    DESCRIPTION
            "Specifies the second cBlade NIC of a rEth."

        ::=     { rEthEntry 7 }


rEthInterface2IndexOid OBJECT-TYPE
    SYNTAX      OBJECT IDENTIFIER
    MAX-ACCESS  read-only
    STATUS      current
    DESCRIPTION
            "An encoding of the cBlade Eth BladeFrameIndex, cBladeIndex, and
            cBladeEth index, uniquely identifying the cBlade Eth configured
            as 'interface2'."

        ::=     { rEthEntry 8 }


rEthMACAddressOctets OBJECT-TYPE
    SYNTAX      PhysAddress
    MAX-ACCESS  read-only
    STATUS      current
    DESCRIPTION
            "This object is deprecated"

        ::=     { rEthEntry 9 }


rEthMACAddressString OBJECT-TYPE
    SYNTAX      DisplayString
    MAX-ACCESS  read-only
    STATUS      current
    DESCRIPTION
            "This object is deprecated"

        ::=     { rEthEntry 10 }


rEthFlowControlOn OBJECT-TYPE
    SYNTAX      TruthValue
    MAX-ACCESS  read-only
    STATUS      current
    DESCRIPTION
            "Indicates whether flow-control is currently enabled for this
            rEth."

        ::=     { rEthEntry 11 }


rEthAutoMACAssign OBJECT-TYPE
    SYNTAX      TruthValue
    MAX-ACCESS  read-only
    STATUS      current
    DESCRIPTION
            "This object is deprecated"

        ::=     { rEthEntry 12 }


rEthLoadBalancePolicy OBJECT-TYPE
    SYNTAX      LoadBalanceType
    MAX-ACCESS  read-only
    STATUS      current
    DESCRIPTION
            "Describes the rEth Load Balancing Policy:
              pair(1)
                (default) packets are transmitted on the same cBlade
                that is receiving packets.
              inverse(2)
                packets are transmitted on the failover partner not currently
                enabled
              balance(3)
                packets are transmitted via either cBlade. With this option, a
                pBlade attempts to load-balance between both cBlades.
                NOTE: Certain external switches may not allow this
                configuration.
              undefined(999)"

        ::=     { rEthEntry 13 }


rEthState OBJECT-TYPE
    SYNTAX      REthStateType
    MAX-ACCESS  read-only
    STATUS      current
    DESCRIPTION
            "Describes the current State of the REth:
                redundant(1)
                    both eths are not failed
                not-redundant(2)
                    one of the two eths is known to be failed
                degraded(3)
                    one of the two eths is known to be failed,
                    and the other is unknown
                failed(4)
                    both eths are known to be failed
                unknown(999)"

        ::=     { rEthEntry 14 }

rEthFrameIndex OBJECT-TYPE
    SYNTAX      Integer32 (1..2147483647)
    MAX-ACCESS  read-only
    STATUS      current
    DESCRIPTION
            "An integer value uniquely identifying the BladeFrame that hosts
            this rEth.  Prior to PAN Manager 5.0, all rEths belonged to the
            same BladeFrame.  With BladeFarms, we need to identify the
            BladeFrame that hosts each rEth."

        ::=     { rEthEntry 15 }

rEthMTUSize OBJECT-TYPE
    SYNTAX      Integer32
    MAX-ACCESS  read-only
    STATUS      current
    DESCRIPTION
            "Defines the MTU size of a rEth."

        ::=     { rEthEntry 16 }


-- Mega REths comprised on REths on multiple Frames in the PAN,
-- provide consistant network access to pServers, so that pServers
-- may failover from a Blade in one Frame to a Blade in another.
megaREths OBJECT IDENTIFIER ::= { devices 6 }

megaREthTable   OBJECT-TYPE
    SYNTAX      SEQUENCE OF MegaREthEntry
    MAX-ACCESS  not-accessible
    STATUS      current
    DESCRIPTION
            "A list of MegaREth entries containing information about each
            Mega REth in the PAN.  An MegaREth consists of zero or more REths,
            usually each on a different Frame."

        ::=     { megaREths 1 }


megaREthEntry OBJECT-TYPE
    SYNTAX      MegaREthEntry
    MAX-ACCESS  not-accessible
    STATUS      current
    DESCRIPTION
            "Information specific to each rEth in the PAN."

    INDEX       { megaREthIndex }
        ::=     { megaREthTable 1 }

MegaREthEntry ::=
    SEQUENCE {
        megaREthIndex
            Integer32,
        megaREthName
            DisplayString
    }

megaREthIndex OBJECT-TYPE
    SYNTAX      Integer32 (1..2147483647)
    MAX-ACCESS  read-only
    STATUS      current
    DESCRIPTION
            "An integer value uniquely identifying the MegaREth within the PAN"

        ::=     { megaREthEntry 1 }

megaREthName OBJECT-TYPE
    SYNTAX      DisplayString
    MAX-ACCESS  read-only
    STATUS      current
    DESCRIPTION
            "A human readable string uniquely identifying the MegaREth."

        ::=     { megaREthEntry 2 }


-- identify REths belonging to an MegaREth
megaREthMemberTable   OBJECT-TYPE
    SYNTAX      SEQUENCE OF MegaREthMemberEntry
    MAX-ACCESS  not-accessible
    STATUS      current
    DESCRIPTION
            "A list of REths belonging to each MegaREth."
        ::=     { megaREths 2 }


megaREthMemberEntry OBJECT-TYPE
    SYNTAX      MegaREthMemberEntry
    MAX-ACCESS  not-accessible
    STATUS      current
    DESCRIPTION
            "Information specific to each rEth in the PAN."

    INDEX       { megaREthMemberMegaREthIndex, megaREthMemberREthIndex }
        ::=     { megaREthMemberTable 1 }

MegaREthMemberEntry ::=
    SEQUENCE {
        megaREthMemberMegaREthIndex
            Integer32,
        megaREthMemberREthIndex
            Integer32,
        megaREthMemberREthName
            DisplayString
    }

megaREthMemberMegaREthIndex OBJECT-TYPE
    SYNTAX      Integer32 (1..2147483647)
    MAX-ACCESS  read-only
    STATUS      current
    DESCRIPTION
            "An integer value identifying the megaREthIndex value of the
            MegaREth containing the REth indenified by this entry."

        ::=     { megaREthMemberEntry 1 }

megaREthMemberREthIndex OBJECT-TYPE
    SYNTAX      Integer32 (1..2147483647)
    MAX-ACCESS  read-only
    STATUS      current
    DESCRIPTION
            "An integer value identifying the rEthIndex value of the
            REth contained by the MegaREth indenified by this entry."

        ::=     { megaREthMemberEntry 2 }

megaREthMemberREthName OBJECT-TYPE
    SYNTAX      DisplayString
    MAX-ACCESS  read-only
    STATUS      current
    DESCRIPTION
            "A human readable string uniquely identifying the REth
            conainted by the MegaREth identified by this entry"

        ::=     { megaREthMemberEntry 3 }




vSwitches OBJECT IDENTIFIER ::= { devices 4 }

vSwitchTable   OBJECT-TYPE
    SYNTAX      SEQUENCE OF VSwitchEntry
    MAX-ACCESS  not-accessible
    STATUS      current
    DESCRIPTION
            "A Table of information specific to vSwitches within the PAN.

            vSwitches establish connectivity between pServers and external
            networks or between pServers.

            Internal  Connectivity  -  LPAN Administrators can create Eths
                for pBlade-to-pBlade communication using any vSwitch they
                have permission to access. If two pServers connect to the
                same vSwitch, the two pServers can communicate via IP.

            External Connectivity - BladeFrame architecture only supports
                external network communication through a Redundant Ethernet
                (rEth) configuration. PAN or BladeFrame Administrators can
                only create vSwitches for external connectivity using an
                uplink configured with the 'reth' command. "

        ::=     { vSwitches 1 }


vSwitchEntry OBJECT-TYPE
    SYNTAX      VSwitchEntry
    MAX-ACCESS  not-accessible
    STATUS      current
    DESCRIPTION
            "Information specific to each vSwitch in the PAN, or allocated to
            the LPAN if LPAN agent."

    INDEX       { vSwitchIndex }
        ::=     { vSwitchTable 1 }

VSwitchEntry ::=
    SEQUENCE {
        vSwitchIndex
            Integer32,
        vSwitchName
            DisplayString,
        vSwitchRedundant
            TruthValue,
        vSwitchExternal
            TruthValue,
        vSwitchRouterIp
            DisplayString,
        vSwitchDHCPProxyIp
            DisplayString,
        vSwitchRethName
            DisplayString,
        vSwitchRethIndex
            Integer32,
        vSwitchUplinkName
            DisplayString,
        vSwitchUplinkPort
            Integer32,
        vSwitchVLANId
            Integer32,
        vSwitchVLANName
            DisplayString,
        vSwitchMRethName
            DisplayString,
        vSwitchMRethIndex
            Integer32
    }


vSwitchIndex OBJECT-TYPE
    SYNTAX      Integer32 (1..2147483647)
    MAX-ACCESS  read-only
    STATUS      current
    DESCRIPTION
            "An integer value uniquely identifying this vSwitch"

        ::=     { vSwitchEntry 1 }


vSwitchName OBJECT-TYPE
    SYNTAX      DisplayString
    MAX-ACCESS  read-only
    STATUS      current
    DESCRIPTION
            "A human readable string uniquely identifying this switch."

        ::=     { vSwitchEntry 2 }


vSwitchRedundant OBJECT-TYPE
    SYNTAX      TruthValue
    MAX-ACCESS  read-only
    STATUS      current
    DESCRIPTION
            "indicates whether or not this vSwitch is configured for
            uplink redundancy."

        ::=     { vSwitchEntry 3 }


vSwitchExternal OBJECT-TYPE
    SYNTAX      TruthValue
    MAX-ACCESS  read-only
    STATUS      current
    DESCRIPTION
            "indicates whether or not this vSwitch is configured provide
            external IP connectivity."

        ::=     { vSwitchEntry 4 }


vSwitchRouterIp OBJECT-TYPE
    SYNTAX      DisplayString
    MAX-ACCESS  read-only
    STATUS      current
    DESCRIPTION
            "This object is deprecated."

        ::=     { vSwitchEntry 5 }


vSwitchDHCPProxyIp OBJECT-TYPE
    SYNTAX      DisplayString
    MAX-ACCESS  read-only
    STATUS      current
    DESCRIPTION
            "This object is deprecated."

        ::=     { vSwitchEntry 6 }


vSwitchRethName OBJECT-TYPE
    SYNTAX      DisplayString
    MAX-ACCESS  read-only
    STATUS      current
    DESCRIPTION
            "A textual string identifying the name of the rEth uplink,
            if configured."

        ::=     { vSwitchEntry 7 }

vSwitchRethIndex OBJECT-TYPE
    SYNTAX      Integer32
    MAX-ACCESS  read-only
    STATUS      current
    DESCRIPTION
            "An encoding of the rEthIndex value of the rEth uplink,
            or -1 if none."

        ::=     { vSwitchEntry 8 }


vSwitchUplinkName OBJECT-TYPE
    SYNTAX      DisplayString
    MAX-ACCESS  read-only
    STATUS      current
    DESCRIPTION
            "This object is deprecated.  As of release 4.0, uplink names and ports
             are associated with cBlade eths, not vSwitches."

        ::=     { vSwitchEntry 9 }


vSwitchUplinkPort OBJECT-TYPE
    SYNTAX      Integer32
    MAX-ACCESS  read-only
    STATUS      current
    DESCRIPTION
            "This object is deprecated.  As of release 4.0, uplink names and ports
             are associated with cBlade eths, not vSwitches."

        ::=     { vSwitchEntry 10 }


vSwitchVLANId OBJECT-TYPE
    SYNTAX      Integer32
    MAX-ACCESS  read-only
    STATUS      current
    DESCRIPTION
            "specifies a VLAN ID assigned to the uplink port of this vSwitch,
             or -1 for none"

        ::=     { vSwitchEntry 11 }


vSwitchVLANName OBJECT-TYPE
    SYNTAX      DisplayString
    MAX-ACCESS  read-only
    STATUS      current
    DESCRIPTION
            "specifies a VLAN Name assigned to the uplink port of this vSwitch."

        ::=     { vSwitchEntry 12 }

vSwitchMRethName OBJECT-TYPE
    SYNTAX      DisplayString
    MAX-ACCESS  read-only
    STATUS      current
    DESCRIPTION
            "A textual string identifying the name of the Mega REth uplink,
            if configured."

        ::=     { vSwitchEntry 13 }

vSwitchMRethIndex OBJECT-TYPE
    SYNTAX      Integer32 (1..2147483647)
    MAX-ACCESS  read-only
    STATUS      current
    DESCRIPTION
            "An encoding of the megaREthIndex value of the Mega REth uplink,
            or -1 if none."

        ::=     { vSwitchEntry 14 }



-- vSwitch to LPAN allocations

vSwitchLPanAllocTable  OBJECT-TYPE
    SYNTAX      SEQUENCE OF VSwitchLPanAllocEntry
    MAX-ACCESS  not-accessible
    STATUS      current
    DESCRIPTION
            "A list of LPAN indicies identifying LPAN vSwitch allocations."

        ::=     { vSwitches 2 }


vSwitchLPanAllocEntry OBJECT-TYPE
    SYNTAX      VSwitchLPanAllocEntry
    MAX-ACCESS  not-accessible
    STATUS      current
    DESCRIPTION
            "Information specific to each LPAN vSwitch allocation."

    INDEX       { lPanIndex, vSwitchIndex }
        ::=     { vSwitchLPanAllocTable 1 }


VSwitchLPanAllocEntry ::=
    SEQUENCE {
        vSwitchLPanAllocVSwitchIndex
             Integer32,
        vSwitchLPanAllocLPanIndex
            Integer32
    }


vSwitchLPanAllocVSwitchIndex OBJECT-TYPE
    SYNTAX      Integer32
    MAX-ACCESS  read-only
    STATUS      current
    DESCRIPTION
            "An integer index unquely identifying the vSwitch within the
            LPAN."

        ::=     { vSwitchLPanAllocEntry 1 }


vSwitchLPanAllocLPanIndex OBJECT-TYPE
    SYNTAX      Integer32
    MAX-ACCESS  read-only
    STATUS      current
    DESCRIPTION
            "The lpanIndex of the LPAN hosting the LPAN this vSwitch is
            allocated to."

        ::=     { vSwitchLPanAllocEntry 2 }


-- vSwitch to pServer allocations

vSwitchPSvrAllocTable   OBJECT-TYPE
    SYNTAX      SEQUENCE OF VSwitchPSvrAllocEntry
    MAX-ACCESS  not-accessible
    STATUS      current
    DESCRIPTION
            "A list of LPAN, pServer index pairs identifying pServer vSwitch
            allocations."

        ::=     { vSwitches 3 }


vSwitchPSvrAllocEntry OBJECT-TYPE
    SYNTAX      VSwitchPSvrAllocEntry
    MAX-ACCESS  not-accessible
    STATUS      current
    DESCRIPTION
            "Information specific to each pServer vSwitch allocation."

    INDEX       { vSwitchIndex, lPanIndex, pServerIndex, pServerEthIndex }
        ::=     { vSwitchPSvrAllocTable 1 }


VSwitchPSvrAllocEntry ::=
    SEQUENCE {
        vSwitchPSvrAllocVSwitchIndex
            Integer32,
        vSwitchPSvrAllocLPanIndex
            Integer32,
        vSwitchPSvrAllocPSvrIndex
            Integer32,
        vSwtichPSvrAllocEthIndex
            Integer32
    }


vSwitchPSvrAllocVSwitchIndex OBJECT-TYPE
    SYNTAX      Integer32 (1..2147483647)
    MAX-ACCESS  read-only
    STATUS      current
    DESCRIPTION
            "The vSwitchIndex value of the switch that this allocation
            applies to."

        ::=     { vSwitchPSvrAllocEntry 1 }


vSwitchPSvrAllocLPanIndex OBJECT-TYPE
    SYNTAX      Integer32 (1..2147483647)
    MAX-ACCESS  read-only
    STATUS      current
    DESCRIPTION
            "The lpanIndex of the LPAN hosting the pServer this vSwitch is
            allocated to."

        ::=     { vSwitchPSvrAllocEntry 2 }


vSwitchPSvrAllocPSvrIndex OBJECT-TYPE
    SYNTAX      Integer32 (1..2147483647)
    MAX-ACCESS  read-only
    STATUS      current
    DESCRIPTION
            "The pServerIndex value of the pServer hosting the pServer this
            vSwitch is allocated to."

        ::=     { vSwitchPSvrAllocEntry 3 }


vSwtichPSvrAllocEthIndex OBJECT-TYPE
    SYNTAX      Integer32 (1..2147483647)
    MAX-ACCESS  read-only
    STATUS      current
    DESCRIPTION
            "The pServerEthIndex value of the Eth on the pServer indicated by
            vSwitchPSvrAllocLPanIndex, vSwitchPSvrAllocPSvrIndex that this vSwitch
            is mapped to."

        ::=     { vSwitchPSvrAllocEntry 4 }



-- LPANs group
--   Contains information & controls for logical PANs in the Egenera PAN.


-- LPANs group
--
-- Information about LPANs and LPAN subelements (pServers, applications)

lPans     OBJECT IDENTIFIER ::= { management 4 }


lPanTable OBJECT-TYPE
    SYNTAX      SEQUENCE OF LPanEntry
    MAX-ACCESS  not-accessible
    STATUS      current
    DESCRIPTION
            "A list of entries containing information and controls for
            LPANs."
        ::=     { lPans 1 }


lPanEntry OBJECT-TYPE
    SYNTAX      LPanEntry
    MAX-ACCESS  not-accessible
    STATUS      current
    DESCRIPTION
            "A LPAN entry contains information and controls for
            LPANs."

    INDEX       { lPanIndex }
        ::=     { lPanTable 1}


LPanEntry ::=
    SEQUENCE {
        lPanIndex
            Integer32,
        lPanName
            DisplayString,
        lPanHealthStatus
            HealthStatusType,
        lPanUpTime
            TimeTicks
    }


lPanIndex OBJECT-TYPE
    SYNTAX      Integer32 (1..2147483647)
    MAX-ACCESS  read-only
    STATUS      current
    DESCRIPTION
            "An integer value uniquely identifying the LPAN."

        ::=     { lPanEntry 1}


lPanName OBJECT-TYPE
    SYNTAX      DisplayString
    MAX-ACCESS  read-only
    STATUS      current
    DESCRIPTION
            "A textual string identifying the LPAN."

        ::=     { lPanEntry 2 }

lPanHealthStatus OBJECT-TYPE
    SYNTAX      HealthStatusType
    MAX-ACCESS  read-only
    STATUS      current
    DESCRIPTION
            "An indication of the health of the LPAN."

        ::=     { lPanEntry 3 }


lPanUpTime OBJECT-TYPE
    SYNTAX      TimeTicks
    MAX-ACCESS  read-only
    STATUS      current
    DESCRIPTION
            "Deprecated, as of release 4.0, LPANs no longer have a concept
            of uptime."

        ::=     { lPanEntry 4 }


-- LogicalPAN Control Table
-- The table provides controls for logical PANs.

lPanControlTable OBJECT-TYPE
    SYNTAX      SEQUENCE OF LPanControlEntry
    MAX-ACCESS  not-accessible
    STATUS      current
    DESCRIPTION
            "A list of LPAN control entries containing controls for
            LPANs in the Egenera PAN."

        ::=     { lPans 2 }


lPanControlEntry OBJECT-TYPE
    SYNTAX      LPanControlEntry
    MAX-ACCESS  not-accessible
    STATUS      current
    DESCRIPTION
            "A logical PAN entry contains controls for LPANs in the
            Egenera PAN."

    INDEX       { lPanIndex }
        ::=     { lPanControlTable 1}


LPanControlEntry ::=
    SEQUENCE {
        lPanBoot
            Integer32,
        lPanReboot
            Integer32,
        lPanDoShutdown
            Integer32,
        lPanCheckHealth
            Integer32,
        lPanUpdate
            Integer32
    }


lPanBoot OBJECT-TYPE
    SYNTAX      Integer32
    MAX-ACCESS  read-write
    STATUS      current
    DESCRIPTION
            "When set to 1, invokes a boot operation on the LPAN.
            When read, returns 0."

        ::=     { lPanControlEntry 1 }


lPanReboot OBJECT-TYPE
    SYNTAX      Integer32
    MAX-ACCESS  read-write
    STATUS      current
    DESCRIPTION
            "When set to 1, invokes a reboot operation on the LPAN.
            When read, returns 0."

        ::=     { lPanControlEntry 2 }


lPanDoShutdown OBJECT-TYPE
    SYNTAX      Integer32
    MAX-ACCESS  read-write
    STATUS      current
    DESCRIPTION
            "When set to 1, invokes a shutdown operation on the LPAN.
            When read, returns 0."

        ::=     { lPanControlEntry 3 }


lPanCheckHealth OBJECT-TYPE
    SYNTAX      Integer32
    MAX-ACCESS  read-write
    STATUS      current
    DESCRIPTION
            "When set to 1, invokes a checkhealth operation on the Logical
            PAN. When read, returns 0."

        ::=     { lPanControlEntry 4 }


lPanUpdate OBJECT-TYPE
    SYNTAX      Integer32
    MAX-ACCESS  read-write
    STATUS      current
    DESCRIPTION
            "When set to 1, invokes a update operation on the LPAN.
            When read, returns 0."

        ::=     { lPanControlEntry 5 }


-- Pools group
-- Information about Pools(Global Pools and Local Pools)

PoolType ::= TEXTUAL-CONVENTION
    STATUS      current
    DESCRIPTION
            "Describes type of blade pool."
    SYNTAX INTEGER {
        global(1),
        local(2),
        unknown(999)
    }

pools     OBJECT IDENTIFIER ::= { management 5 }

poolTable OBJECT-TYPE
    SYNTAX      SEQUENCE OF PoolEntry
    MAX-ACCESS  not-accessible
    STATUS      current
    DESCRIPTION
            "A list of entries containing information for
             Global Pools and Local Pools."
        ::=     { pools 1 }


poolEntry OBJECT-TYPE
    SYNTAX      PoolEntry
    MAX-ACCESS  not-accessible
    STATUS      current
    DESCRIPTION
            "A Pool entry contains information for
            Global Pools and Local Pools."

    INDEX       { poolIndex }
        ::=     { poolTable 1}


PoolEntry ::=
    SEQUENCE {
        poolIndex
            Integer32,
        poolName
            DisplayString,
        poolDescription
            DisplayString,
        poolLinkedIndex
            Integer32,
        poolType
            PoolType,
        poolAvailableBlades
            Integer32
    }


poolIndex OBJECT-TYPE
    SYNTAX      Integer32 (1..2147483647)
    MAX-ACCESS  read-only
    STATUS      current
    DESCRIPTION
            "An integer value uniquely identifying the pool."

        ::=     { poolEntry 1}


poolName OBJECT-TYPE
    SYNTAX      DisplayString
    MAX-ACCESS  read-only
    STATUS      current
    DESCRIPTION
            "A textual string identifying the pool."

        ::=     { poolEntry 2 }


poolDescription OBJECT-TYPE
    SYNTAX      DisplayString
    MAX-ACCESS  read-only
    STATUS      current
    DESCRIPTION
            "A textual string describing the pool."

        ::=     { poolEntry 3 }


poolLinkedIndex OBJECT-TYPE
    SYNTAX      Integer32 (1..2147483647)
    MAX-ACCESS  read-only
    STATUS      current
    DESCRIPTION
            "For local pools, the poolIndex of the global pool that
            the local pool is linked to, or -1 if not linked.  For
            Global Pools, this value is -1."

        ::=     { poolEntry 4}


poolType OBJECT-TYPE
    SYNTAX      PoolType
    MAX-ACCESS  read-only
    STATUS      current
    DESCRIPTION
            "Indicates the type of pool (global or local)."

        ::=     { poolEntry 5}


poolAvailableBlades OBJECT-TYPE
    SYNTAX      Integer32 (0..2147483647)
    MAX-ACCESS  read-only
    STATUS      current
    DESCRIPTION
            "Indicates the number of blades currently available in
            the pool."

        ::=     { poolEntry 6}



-- pServers group
-- Contains information and controls for pServers.  A pServer is the
-- combination of a single pBlade, disk resources, and network
-- resources which provides the capabilities of a conventional server.

pServers        OBJECT IDENTIFIER ::= { lPans 3 }


pServerTable   OBJECT-TYPE
    SYNTAX      SEQUENCE OF PServerEntry
    MAX-ACCESS  not-accessible
    STATUS      current
    DESCRIPTION
            "A list of pServer entries containing information about each
            pServer."

        ::=     { pServers 1 }


pServerEntry OBJECT-TYPE
    SYNTAX      PServerEntry
    MAX-ACCESS  not-accessible
    STATUS      current
    DESCRIPTION
            "Information regarding each pServer."

    INDEX       { lPanIndex, pServerIndex }
        ::=     { pServerTable 1 }


PServerEntry ::=
    SEQUENCE {
        pServerIndex
            Integer32,
        pServerLPanIndex
            Integer32,
        pServerBladeIndex
            Integer32,
        pServerBladeFrameIndex
            Integer32,
        pServerName
            DisplayString,
        pServerFullName
            DisplayString,
        pServerDescription
            DisplayString,
        pServerBladeFrameName
            DisplayString,
        pServerPBladeName
            DisplayString,
        pServerLPanName
            DisplayString,
        pServerValidBootDisk
            TruthValue,
        pServerHostname
            DisplayString,
        pServerAgentAvailable
            TruthValue,
        pServerHealthStatus
            HealthStatusType,
        pServerInDebugger
            TruthValue,
        pServerAutoActivate
            TruthValue,
        pServerAutoBoot
            TruthValue,
        pServerActivateOrder
            Integer32,
        pServerActive
            TruthValue,
        pServerBootStatus
            DisplayString,
        pServerUptime
            TimeTicks,
        pServerFailedOver
            TruthValue,
        pServerOptional
            TruthValue,
        pServerShutdownTimeout
            Integer32,
        pServerPrimaryPBladeIndex
            Integer32,
        pServerPrimaryPBladeFrameIndex
            Integer32,
        pServerPrimaryPBladeName
            DisplayString,
        pServerFailoverPBladeIndex
            Integer32,
        pServerFailoverPBladeFrameIndex
            Integer32,
        pServerFailoverPBladeName
            DisplayString,
        pServerVBladeIndex
            Integer32
    }


pServerIndex OBJECT-TYPE
    SYNTAX      Integer32 (1..2147483647)
    MAX-ACCESS  read-only
    STATUS      current
    DESCRIPTION
            "An integer value uniquely identifying pServer within Logical
            PAN."

        ::=     { pServerEntry 1 }

pServerLPanIndex OBJECT-TYPE
    SYNTAX      Integer32 (1..2147483647)
    MAX-ACCESS  read-only
    STATUS      current
    DESCRIPTION
            "An integer value identifying the lPanIndex value of the
            LPAN that hosts this pServer."

        ::=     { pServerEntry 2 }


pServerBladeIndex OBJECT-TYPE
    SYNTAX      Integer32 (-1..2147483647)
    MAX-ACCESS  read-only
    STATUS      current
    DESCRIPTION
            "An integer value identifying the pBladeIndex value of
            the pBlade that currently hosts this pServer, -1 if no
            current pBlade"

        ::=     { pServerEntry 3 }


pServerBladeFrameIndex OBJECT-TYPE
    SYNTAX      Integer32 (-1..2147483647)
    MAX-ACCESS  read-only
    STATUS      current
    DESCRIPTION
            "An integer value identifying the bladeFrameIndex value of the
            BladeFrame that currently hosts this pServer, -1 if no
            current pBlade"

        ::=     { pServerEntry 4 }


pServerName OBJECT-TYPE
    SYNTAX      DisplayString
    MAX-ACCESS  read-only
    STATUS      current
    DESCRIPTION
            "A textual string identifying this pServer."

        ::=     { pServerEntry 5 }


pServerFullName OBJECT-TYPE
    SYNTAX      DisplayString
    MAX-ACCESS  read-only
    STATUS      current
    DESCRIPTION
            "A textual string fully identifying this pServer and its LPAN."

        ::=     { pServerEntry 6 }


pServerDescription OBJECT-TYPE
    SYNTAX      DisplayString
    MAX-ACCESS  read-only
    STATUS      current
    DESCRIPTION
            "A textual string describing this pServer."

        ::=     { pServerEntry 7 }


pServerBladeFrameName OBJECT-TYPE
    SYNTAX      DisplayString
    MAX-ACCESS  read-only
    STATUS      current
    DESCRIPTION
            "A textual string identifying the BladeFrame hosting this
            PServer."

        ::=     { pServerEntry 8 }


pServerPBladeName OBJECT-TYPE
    SYNTAX      DisplayString
    MAX-ACCESS  read-only
    STATUS      current
    DESCRIPTION
            "A textual string identifying the pBlade currently hosting this
            pServer."

        ::=     { pServerEntry 9 }


pServerLPanName OBJECT-TYPE
    SYNTAX      DisplayString
    MAX-ACCESS  read-only
    STATUS      current
    DESCRIPTION
            "A textual string identifying the LPAN containing this pServer."

        ::=     { pServerEntry 10 }


pServerValidBootDisk OBJECT-TYPE
    SYNTAX      TruthValue
    MAX-ACCESS  read-only
    STATUS      current
    DESCRIPTION
            "This object is deprecated."

        ::=     { pServerEntry 11 }


pServerHostname OBJECT-TYPE
    SYNTAX      DisplayString
    MAX-ACCESS  read-only
    STATUS      current
    DESCRIPTION
            "The hostname of this pServer."

        ::=     { pServerEntry 12 }


pServerAgentAvailable OBJECT-TYPE
    SYNTAX      TruthValue
    MAX-ACCESS  read-only
    STATUS      current
    DESCRIPTION
            "Indicates whether the Egenera management agent is running
            on the pBlade hosting this pServer."

        ::=     { pServerEntry 13 }


pServerHealthStatus OBJECT-TYPE
    SYNTAX      HealthStatusType
    MAX-ACCESS  read-only
    STATUS      current
    DESCRIPTION
            "Indicates the current health of the pServer."

        ::=     { pServerEntry 14 }


pServerInDebugger OBJECT-TYPE
    SYNTAX      TruthValue
    MAX-ACCESS  read-only
    STATUS      current
    DESCRIPTION
            "This object is deprecated as of PAN Manager release 4.0.  The
            value may be obtained via the pBlade table."

        ::=     { pServerEntry 15 }


pServerAutoActivate OBJECT-TYPE
    SYNTAX      TruthValue
    MAX-ACCESS  read-only
    STATUS      current
    DESCRIPTION
            "This object is deprecated as of PAN Manager release 4.0."

        ::=     { pServerEntry 16 }


pServerAutoBoot OBJECT-TYPE
    SYNTAX      TruthValue
    MAX-ACCESS  read-only
    STATUS      current
    DESCRIPTION
            "This object is deprecated as of PAN Manager release 4.0."

        ::=     { pServerEntry 17 }


pServerActivateOrder OBJECT-TYPE
    SYNTAX      Integer32
    MAX-ACCESS  read-only
    STATUS      current
    DESCRIPTION
            "Indicates the order within the LPAN that this pServer is
            activated."

        ::=     { pServerEntry 18 }


pServerActive OBJECT-TYPE
    SYNTAX      TruthValue
    MAX-ACCESS  read-only
    STATUS      current
    DESCRIPTION
            "This object is deprecated as of PAN Manager release 4.0."

        ::=     { pServerEntry 19 }


pServerBootStatus OBJECT-TYPE
    SYNTAX      DisplayString
    MAX-ACCESS  read-only
    STATUS      current
    DESCRIPTION
            "Describes the current boot status"

        ::=     { pServerEntry 20 }


pServerUptime OBJECT-TYPE
    SYNTAX      TimeTicks
    MAX-ACCESS  read-only
    STATUS      current
    DESCRIPTION
            "The length of time the pServer has been up in 1/100ths of a
            second."

        ::=     { pServerEntry 21 }


pServerFailedOver OBJECT-TYPE
    SYNTAX      TruthValue
    MAX-ACCESS  read-only
    STATUS      current
    DESCRIPTION
            "This object is deprecated as of PAN Manager release 4.0."

        ::=     { pServerEntry 22 }


pServerOptional OBJECT-TYPE
    SYNTAX      TruthValue
    MAX-ACCESS  read-only
    STATUS      current
    DESCRIPTION
            "Indicates whether this pServer has been designated as optional."

        ::=     { pServerEntry 23 }


pServerShutdownTimeout OBJECT-TYPE
    SYNTAX      Integer32
    MAX-ACCESS  read-only
    STATUS      current
    DESCRIPTION
            "The amount of time given for the pServer to shutdown before the
            shutdown operation is deemed to have failed."

        ::=     { pServerEntry 24 }


pServerPrimaryPBladeIndex OBJECT-TYPE
    SYNTAX      Integer32 (-2..2147483647)
    MAX-ACCESS  read-only
    STATUS      current
    DESCRIPTION
            "The pBladeIndex value of the pServer's configured primary pBlade.
            -1 indicates none, -2 indicates global or local pool."

        ::=     { pServerEntry 25 }


pServerPrimaryPBladeFrameIndex OBJECT-TYPE
    SYNTAX      Integer32  (-2..2147483647)
    MAX-ACCESS  read-only
    STATUS      current
    DESCRIPTION
            "The bladeFrameIndex value of BladeFrame hosting the pServer's
            configured primary pBlade.  -1 indicates none, -2 indicates global
            or local pool."

        ::=     { pServerEntry 26 }


pServerPrimaryPBladeName OBJECT-TYPE
    SYNTAX      DisplayString
    MAX-ACCESS  read-only
    STATUS      current
    DESCRIPTION
            "A textual string including the Frame and pBlade name of this
            pServer's configured primary pBlade.  'pool' indicates global
            or local pool."

        ::=     { pServerEntry 27 }


pServerFailoverPBladeIndex OBJECT-TYPE
    SYNTAX      Integer32 (-2..2147483647)
    MAX-ACCESS  read-only
    STATUS      current
    DESCRIPTION
            "The pBladeIndex value of the pServer's configured failover pBlade.
            -1 indicates none, -2 indicates global or local pool."

        ::=     { pServerEntry 28 }



pServerFailoverPBladeFrameIndex OBJECT-TYPE
    SYNTAX      Integer32  (-2..2147483647)
    MAX-ACCESS  read-only
    STATUS      current
    DESCRIPTION
            "The bladeFrameIndex value of BladeFrame hosting the pServer's
            configured failover pBlade.  -1 indicates none, -2 indicates global
            or local pool."

        ::=     { pServerEntry 29 }


pServerFailoverPBladeName OBJECT-TYPE
    SYNTAX      DisplayString
    MAX-ACCESS  read-only
    STATUS      current
    DESCRIPTION
            "A textual string including the Frame and pBlade name of this
            pServer's configured failover pBlade.  'pool' indicates global
            or local pool."

        ::=     { pServerEntry 30 }


pServerVBladeIndex OBJECT-TYPE
    SYNTAX      Integer32  (-2..2147483647)
    MAX-ACCESS  read-only
    STATUS      current
    DESCRIPTION
            "An integer value identifying the vBladeIndex value of
            the vBlade that currently hosts this pServer, -1 if no
            current vBlade, or if the pServer is hosted by a pBlade.
            See pServerBladeIndex"

        ::=     { pServerEntry 31 }

-- pServerStatsTable
-- contains runtime statistics for each pServer.  This table is present when
-- the Egenera management agent is running on the pBlade, and statistic
-- collection is enabled.

pServerStatsTable  OBJECT-TYPE
    SYNTAX      SEQUENCE OF PServerStatsEntry
    MAX-ACCESS  not-accessible
    STATUS      current
    DESCRIPTION
            "A list of pServer Monitor entries containing runtime statistics
            for pServers."

        ::=     { pServers 2 }


pServerStatsEntry OBJECT-TYPE
    SYNTAX      PServerStatsEntry
    MAX-ACCESS  not-accessible
    STATUS      current
    DESCRIPTION
            "A pServer Monitor entry contains runtime statistics for
            pServers."

    INDEX       { lPanIndex, pServerIndex }
        ::=     { pServerStatsTable 1 }


PServerStatsEntry ::=
    SEQUENCE {
        pServerStatsUpTime
            TimeTicks,
        pServerStatsLoadAvg1
            Gauge32,
        pServerStatsLoadAvg5
            Gauge32,
        pServerStatsLoadAvg15
            Gauge32,
        pServerStatsCpuUser
            Counter32,
        pServerStatsCpuSystem
            Counter32,
        pServerStatsCpuIdle
            Counter32,
        pServerStatsLoadScale
            Gauge32,
        pServerStatsNumProcs
            Gauge32,
        pServerStatsLastPid
            Integer32,
        pServerStatsContextSwitch
            Counter32,
        pServerStatsInterrupt
            Counter32,
        pServerStatsMemTotal
            Gauge32,
        pServerStatsMemFree
            Gauge32,
        pServerStatsSwapTotal
            Gauge32,
        pServerStatsSwapFree
            Gauge32,
        pServerStatsPageIn
            Counter32,
        pServerStatsPageOut
            Counter32,
        pServerStatsSwapIn
            Counter32,
        pServerStatsSwapOut
            Counter32,
        pServerStatsDiskReads
            Counter32,
        pServerStatsDiskWrites
            Counter32,
        pServerStatsDiskBlkReads
            Counter32,
        pServerStatsDiskBlkWrites
            Counter32,
        pServerStatsCpuUserNice
            Counter32
    }

pServerStatsUpTime OBJECT-TYPE
    SYNTAX      TimeTicks
    MAX-ACCESS  read-only
    STATUS      current
    DESCRIPTION
            "The uptime in 1/100ths of a second for this pServer."

        ::=     { pServerStatsEntry 1 }


pServerStatsLoadAvg1 OBJECT-TYPE
    SYNTAX      Gauge32
    MAX-ACCESS  read-only
    STATUS      current
    DESCRIPTION
            "100 * the average number of jobs in the run queue over the
            previous minute.  Returns 0 for Windows pServers."

        ::=     { pServerStatsEntry 2 }


pServerStatsLoadAvg5 OBJECT-TYPE
    SYNTAX      Gauge32
    MAX-ACCESS  read-only
    STATUS      current
    DESCRIPTION
            "100 * the average number of jobs in the run queue over the
            previous five minutes.  Returns 0 for Windows pServers."

        ::=     { pServerStatsEntry 3 }


pServerStatsLoadAvg15 OBJECT-TYPE
    SYNTAX      Gauge32
    MAX-ACCESS  read-only
    STATUS      current
    DESCRIPTION
            "100 * the average number of jobs in the run queue over the
            previous fifteen minutes.  Returns 0 for Windows pServers."

        ::=     { pServerStatsEntry 4 }


pServerStatsCpuUser OBJECT-TYPE
    SYNTAX      Counter32
    MAX-ACCESS  read-only
    STATUS      current
    DESCRIPTION
            "The number of (1/100)ths of a second that the pServer spent in
            user mode since boot."

        ::=     { pServerStatsEntry 5 }


pServerStatsCpuSystem OBJECT-TYPE
    SYNTAX      Counter32
    MAX-ACCESS  read-only
    STATUS      current
    DESCRIPTION
            "The number of (1/100)ths of a second that the pServer spent in
            system mode since boot."

        ::=     { pServerStatsEntry 6 }


pServerStatsCpuIdle OBJECT-TYPE
    SYNTAX      Counter32
    MAX-ACCESS  read-only
    STATUS      current
    DESCRIPTION
            "The number of (1/100)ths of a second that the pServer spent in
            idle mode since boot."

        ::=     { pServerStatsEntry 7 }


pServerStatsLoadScale OBJECT-TYPE
    SYNTAX      Gauge32
    MAX-ACCESS  read-only
    STATUS      current
    DESCRIPTION
            "The current load scale.  Returns 0 for Windows pServers."

        ::=     { pServerStatsEntry 8 }


pServerStatsNumProcs OBJECT-TYPE
    SYNTAX      Gauge32
    MAX-ACCESS  read-only
    STATUS      current
    DESCRIPTION
            "The current number of processes running on the pServer."

        ::=     { pServerStatsEntry 9 }


pServerStatsLastPid OBJECT-TYPE
    SYNTAX      Integer32
    MAX-ACCESS  read-only
    STATUS      current
    DESCRIPTION
            "The highest allocated process ID on the pServer.  Returns 0
            for Windows pServers."

        ::=     { pServerStatsEntry 10 }


pServerStatsContextSwitch OBJECT-TYPE
    SYNTAX      Counter32
    MAX-ACCESS  read-only
    STATUS      current
    DESCRIPTION
            "The number of context switches undergone by this pServer since
            boot."

        ::=     { pServerStatsEntry 11 }


pServerStatsInterrupt OBJECT-TYPE
    SYNTAX      Counter32
    MAX-ACCESS  read-only
    STATUS      current
    DESCRIPTION
            "The number of interrupts encountered by this pServer since
            boot."

        ::=     { pServerStatsEntry 12 }


pServerStatsMemTotal OBJECT-TYPE
    SYNTAX      Gauge32
    MAX-ACCESS  read-only
    STATUS      current
    DESCRIPTION
            "The total amount of physical RAM in kB for this pServer."

        ::=     { pServerStatsEntry 13 }


pServerStatsMemFree OBJECT-TYPE
    SYNTAX      Gauge32
    MAX-ACCESS  read-only
    STATUS      current
    DESCRIPTION
            "The amount of free physcial RAM in kB for this pServer."

        ::=     { pServerStatsEntry 14 }


pServerStatsSwapTotal OBJECT-TYPE
    SYNTAX      Gauge32
    MAX-ACCESS  read-only
    STATUS      current
    DESCRIPTION
            "The total amount of configured swap memory in kB for this
            pServer."

        ::=     { pServerStatsEntry 15 }


pServerStatsSwapFree OBJECT-TYPE
    SYNTAX      Gauge32
    MAX-ACCESS  read-only
    STATUS      current
    DESCRIPTION
            "The amount of free swap memory in kB for this pServer."

        ::=     { pServerStatsEntry 16 }


pServerStatsPageIn OBJECT-TYPE
    SYNTAX      Counter32
    MAX-ACCESS  read-only
    STATUS      current
    DESCRIPTION
            "The number of pages paged in since boot."

        ::=     { pServerStatsEntry 17 }


pServerStatsPageOut OBJECT-TYPE
    SYNTAX      Counter32
    MAX-ACCESS  read-only
    STATUS      current
    DESCRIPTION
            "The number of pages paged out since boot."

        ::=     { pServerStatsEntry 18 }


pServerStatsSwapIn OBJECT-TYPE
    SYNTAX      Counter32
    MAX-ACCESS  read-only
    STATUS      current
    DESCRIPTION
            "The number of swap pages paged in since boot."

        ::=     { pServerStatsEntry 19 }


pServerStatsSwapOut OBJECT-TYPE
    SYNTAX      Counter32
    MAX-ACCESS  read-only
    STATUS      current
    DESCRIPTION
            "The number of swap pages paged out since boot."

        ::=     { pServerStatsEntry 20 }


pServerStatsDiskReads OBJECT-TYPE
    SYNTAX      Counter32
    MAX-ACCESS  read-only
    STATUS      current
    DESCRIPTION
            "The number of disk reads since boot."

        ::=     { pServerStatsEntry 21 }


pServerStatsDiskWrites OBJECT-TYPE
    SYNTAX      Counter32
    MAX-ACCESS  read-only
    STATUS      current
    DESCRIPTION
            "The number of disk writes since boot."

        ::=     { pServerStatsEntry 22 }


pServerStatsDiskBlkReads OBJECT-TYPE
    SYNTAX      Counter32
    MAX-ACCESS  read-only
    STATUS      current
    DESCRIPTION
            "The number of 1 kB blocks read from disk since boot.
            Returns 0 for Windows pServers."

        ::=     { pServerStatsEntry 23 }


pServerStatsDiskBlkWrites OBJECT-TYPE
    SYNTAX      Counter32
    MAX-ACCESS  read-only
    STATUS      current
    DESCRIPTION
            "The number of of 1 kB blocks written to disk since boot.
            Returns 0 for Windows pServers."

        ::=     { pServerStatsEntry 24 }


pServerStatsCpuUserNice OBJECT-TYPE
    SYNTAX      Counter32
    MAX-ACCESS  read-only
    STATUS      current
    DESCRIPTION
            "The number of (1/100)ths of a second that the pServer spent in
            user nice mode since boot.  Returns 0 for Windows pServers."

        ::=     { pServerStatsEntry 25 }


-- pServer CPU Table
-- Contains information about each CPU on each pServer

pServerCpuTable   OBJECT-TYPE
    SYNTAX      SEQUENCE OF PServerCpuEntry
    MAX-ACCESS  not-accessible
    STATUS      current
    DESCRIPTION
            "A list of CPU statisitcs for each CPU on each pServer."

        ::=     { pServers 3 }


pServerCpuEntry OBJECT-TYPE
    SYNTAX      PServerCpuEntry
    MAX-ACCESS  not-accessible
    STATUS      current
    DESCRIPTION
            "Statistics for each CPU on the pServer."

    INDEX       { lPanIndex, pServerIndex, pServerCpuIndex }
        ::=     { pServerCpuTable 1 }


PServerCpuEntry ::=
    SEQUENCE {
        pServerCpuIndex
            Integer32,
        pServerCpuPServerIndex
            Integer32,
        pServerCpuLPanIndex
            Integer32,
        pServerCpuModelName
            DisplayString,
        pServerCpuModel
            Integer32,
        pServerCpuFamily
            Integer32,
        pServerCpuVendorId
            DisplayString,
        pServerCpuMhz
            Integer32,
        pServerCpuCacheSize
            Integer32,
        pServerCpuName
            DisplayString,
        pServerCpuUser
            Counter32,
        pServerCpuUserNice
            Counter32,
        pServerCpuSystem
            Counter32,
        pServerCpuIdle
            Counter32
    }


pServerCpuIndex OBJECT-TYPE
    SYNTAX      Integer32 (1..2147483647)
    MAX-ACCESS  read-only
    STATUS      current
    DESCRIPTION
            "An integer uniquely identifying this CPU within the pServer."

        ::=     { pServerCpuEntry 1 }


pServerCpuPServerIndex OBJECT-TYPE
    SYNTAX      Integer32 (1..2147483647)
    MAX-ACCESS  read-only
    STATUS      current
    DESCRIPTION
            "An integer value identifying the pServerIndex value of the
            pServer that hosts this CPU."

        ::=     { pServerCpuEntry 2 }


pServerCpuLPanIndex OBJECT-TYPE
    SYNTAX      Integer32 (1..2147483647)
    MAX-ACCESS  read-only
    STATUS      current
    DESCRIPTION
            "An integer value identifying the lPanIndex value of the
            LPAN that hosts this CPU."

        ::=     { pServerCpuEntry 3 }


pServerCpuModelName OBJECT-TYPE
    SYNTAX      DisplayString
    MAX-ACCESS  read-only
    STATUS      current
    DESCRIPTION
            "A textual string representing the CPU model."

        ::=     { pServerCpuEntry 4 }


pServerCpuModel OBJECT-TYPE
    SYNTAX      Integer32
    MAX-ACCESS  read-only
    STATUS      current
    DESCRIPTION
            "An integer value representing the CPU model."

        ::=     { pServerCpuEntry 5 }


pServerCpuFamily OBJECT-TYPE
    SYNTAX      Integer32
    MAX-ACCESS  read-only
    STATUS      current
    DESCRIPTION
            "An integer value representing the CPU family."

        ::=     { pServerCpuEntry 6 }


pServerCpuVendorId OBJECT-TYPE
    SYNTAX      DisplayString
    MAX-ACCESS  read-only
    STATUS      current
    DESCRIPTION
            "A textual string representing the CPU vendor."

        ::=     { pServerCpuEntry 7 }


pServerCpuMhz OBJECT-TYPE
    SYNTAX      Integer32
    MAX-ACCESS  read-only
    STATUS      current
    DESCRIPTION
            "The speed of the CPU in Mhz."

        ::=     { pServerCpuEntry 8 }


pServerCpuCacheSize OBJECT-TYPE
    SYNTAX      Integer32
    MAX-ACCESS  read-only
    STATUS      current
    DESCRIPTION
            "The cache size of the CPU in MB."

        ::=     { pServerCpuEntry 9 }


pServerCpuName OBJECT-TYPE
    SYNTAX      DisplayString
    MAX-ACCESS  read-only
    STATUS      current
    DESCRIPTION
            "A textual string uniquely identifying this CPU."

        ::=     { pServerCpuEntry 10 }


pServerCpuUser OBJECT-TYPE
    SYNTAX      Counter32
    MAX-ACCESS  read-only
    STATUS      current
    DESCRIPTION
            "The number of (1/100)ths of a second that this CPU spent in
            user mode since boot."

        ::=     { pServerCpuEntry 11 }


pServerCpuUserNice OBJECT-TYPE
    SYNTAX      Counter32
    MAX-ACCESS  read-only
    STATUS      current
    DESCRIPTION
            "The number of (1/100)ths of a second that this CPU spent in
            user nice mode since boot."

        ::=     { pServerCpuEntry 12 }


pServerCpuSystem OBJECT-TYPE
    SYNTAX      Counter32
    MAX-ACCESS  read-only
    STATUS      current
    DESCRIPTION
            "The number of (1/100)ths of a second that this CPU spent in
            system mode since boot."

        ::=     { pServerCpuEntry 13 }


pServerCpuIdle OBJECT-TYPE
    SYNTAX      Counter32
    MAX-ACCESS  read-only
    STATUS      current
    DESCRIPTION
            "The number of (1/100)ths of a second that this CPU spent in
            idle mode since boot."

        ::=     { pServerCpuEntry 14 }



-- pServer Disk Table
-- Contains information about each disk on the pServer.

pServerDiskTable OBJECT-TYPE

    SYNTAX      SEQUENCE OF PServerDiskEntry
    MAX-ACCESS  not-accessible
    STATUS      current
    DESCRIPTION
            "A list of disk statisitcs for each disk on the
            pServer."

        ::=     { pServers 4 }

pServerDiskEntry OBJECT-TYPE
    SYNTAX      PServerDiskEntry
    MAX-ACCESS  not-accessible
    STATUS      current
    DESCRIPTION
            "Disk statisitcs for each disk on the pServer."

    INDEX       { lPanIndex, pServerIndex, IMPLIED pServerDiskNameOctets }
        ::=     { pServerDiskTable 1 }

PServerDiskEntry ::=
    SEQUENCE {
        pServerDiskNameOctets
            OCTET STRING,
        pServerDiskPServerIndex
            Integer32,
        pServerDiskLPanIndex
            Integer32,
        pServerDiskName
            DisplayString,
        pServerDiskBlocks
            Gauge32,
        pServerDiskMajor
            Integer32,
        pServerDiskMinor
            Integer32
    }

pServerDiskNameOctets OBJECT-TYPE
    SYNTAX      OCTET STRING (SIZE(0..63))
    MAX-ACCESS  read-only
    STATUS      current
    DESCRIPTION
            "An octet string representing the device special file name
            representing this disk."

        ::=     { pServerDiskEntry 1 }


pServerDiskPServerIndex OBJECT-TYPE
    SYNTAX      Integer32
    MAX-ACCESS  read-only
    STATUS      current
    DESCRIPTION
            "An integer value identifying the pServerIndex value of the
            pServer that utilizes this disk."

        ::=     { pServerDiskEntry 2 }


pServerDiskLPanIndex OBJECT-TYPE
    SYNTAX      Integer32
    MAX-ACCESS  read-only
    STATUS      current
    DESCRIPTION
            "An integer value indentifying the lPanIndex value of the
            LPAN that hosts this disk."

        ::=     { pServerDiskEntry 3 }

pServerDiskName OBJECT-TYPE
    SYNTAX      DisplayString
    MAX-ACCESS  read-only
    STATUS      current
    DESCRIPTION
            "The human readable device special file name representing this
            disk."

        ::=     { pServerDiskEntry 4 }

pServerDiskBlocks OBJECT-TYPE
    SYNTAX      Gauge32
    MAX-ACCESS  read-only
    STATUS      current
    DESCRIPTION
            "The size of this disk in 1kB blocks"

        ::=     { pServerDiskEntry 5 }


pServerDiskMajor OBJECT-TYPE
    SYNTAX      Integer32
    MAX-ACCESS  read-only
    STATUS      current
    DESCRIPTION
            "The major ID of this disk."

        ::=     { pServerDiskEntry 6 }


pServerDiskMinor OBJECT-TYPE
    SYNTAX      Integer32
    MAX-ACCESS  read-only
    STATUS      current
    DESCRIPTION
            "The minor ID of this disk."

        ::=     { pServerDiskEntry 7 }


-- pServer Partition Table
-- Contains information about each disk partition on the pServer.



pServerPartitionTable   OBJECT-TYPE
    SYNTAX      SEQUENCE OF PServerPartitionEntry
    MAX-ACCESS  not-accessible
    STATUS      current
    DESCRIPTION
            "A list of partition statisitcs for each partition on the
            pServer."

        ::=     { pServers 5 }


pServerPartitionEntry OBJECT-TYPE
    SYNTAX      PServerPartitionEntry
    MAX-ACCESS  not-accessible
    STATUS      current
    DESCRIPTION
            "Partition statisitcs for each partition on the pServer."

    INDEX       { lPanIndex, pServerIndex,
                  IMPLIED pServerPartitionNameOctets }
        ::=     { pServerPartitionTable 1 }


PServerPartitionEntry ::=
    SEQUENCE {
        pServerPartitionNameOctets
            OCTET STRING,
        pServerPartitionPServerIndex
            Integer32,
        pServerPartitionLPanIndex
            Integer32,
        pServerPartitionName
            DisplayString,
        pServerPartitionBlocks
            Gauge32,
        pServerPartitionMajor
            Integer32,
        pServerPartitionMinor
            Integer32,
        pServerPartitionFSBlocks
            Gauge32,
        pServerPartitionFSUsedBlocks
            Gauge32,
        pServerPartitionFSAvailableBlocks
            Gauge32,
        pServerPartitionFSUtil
            Gauge32
    }


pServerPartitionNameOctets OBJECT-TYPE
    SYNTAX      OCTET STRING (SIZE(0..63))
    MAX-ACCESS  read-only
    STATUS      current
    DESCRIPTION
            "An octet string representing the device special file name
            representing this disk."

        ::=     { pServerPartitionEntry 1 }


pServerPartitionPServerIndex OBJECT-TYPE
    SYNTAX      Integer32
    MAX-ACCESS  read-only
    STATUS      current
    DESCRIPTION
            "An integer value identifying the pServerIndex value of the
            pServer that utilizes this disk partition."

        ::=     { pServerPartitionEntry 2 }


pServerPartitionLPanIndex OBJECT-TYPE
    SYNTAX      Integer32
    MAX-ACCESS  read-only
    STATUS      current
    DESCRIPTION
            "An integer value indentifying the lPanIndex value of the
            LPAN that hosts this partition."

        ::=     { pServerPartitionEntry 3 }


pServerPartitionName OBJECT-TYPE
    SYNTAX      DisplayString (SIZE(0..127))
    MAX-ACCESS  read-only
    STATUS      current
    DESCRIPTION
            "A textual string identifying the device file that represents
            this partition."

        ::=     { pServerPartitionEntry 4 }


pServerPartitionBlocks OBJECT-TYPE
    SYNTAX      Gauge32
    MAX-ACCESS  read-only
    STATUS      current
    DESCRIPTION
            "The size of this partition in 1kB blocks"

        ::=     { pServerPartitionEntry 5 }


pServerPartitionMajor OBJECT-TYPE
    SYNTAX      Integer32
    MAX-ACCESS  read-only
    STATUS      current
    DESCRIPTION
            "The major ID of this partition."

        ::=     { pServerPartitionEntry 6 }


pServerPartitionMinor OBJECT-TYPE
    SYNTAX      Integer32
    MAX-ACCESS  read-only
    STATUS      current
    DESCRIPTION
            "The minor ID of this partition."

        ::=     { pServerPartitionEntry 7 }


pServerPartitionFSBlocks OBJECT-TYPE
    SYNTAX      Gauge32
    MAX-ACCESS  read-only
    STATUS      current
    DESCRIPTION
            "If the partition contains a mounted filesystem, filesystem size
            in 1k blocks, othewise 0"

        ::=     { pServerPartitionEntry 8 }


pServerPartitionFSUsedBlocks OBJECT-TYPE
    SYNTAX      Gauge32
    MAX-ACCESS  read-only
    STATUS      current
    DESCRIPTION
            "If the partition contains a mounted filesystem, the number of
            used 1k blocks, otherwise 0"

        ::=     { pServerPartitionEntry 9 }


pServerPartitionFSAvailableBlocks OBJECT-TYPE
    SYNTAX      Gauge32
    MAX-ACCESS  read-only
    STATUS      current
    DESCRIPTION
            "If the partition contains a mounted filesystem, the number of
            available 1k blocks, otherwise 0"

        ::=     { pServerPartitionEntry 10 }


pServerPartitionFSUtil OBJECT-TYPE
    SYNTAX      Gauge32
    MAX-ACCESS  read-only
    STATUS      current
    DESCRIPTION
            "If the partition contains a mounted filesystem, the number of
            available 1k blocks, otherwise 0"

        ::=     { pServerPartitionEntry 11 }



-- pServer Virtual Ethernet table
-- Contains information about each network interface on the pServer.


pServerEthTable   OBJECT-TYPE
    SYNTAX      SEQUENCE OF PServerEthEntry
    MAX-ACCESS  not-accessible
    STATUS      current
    DESCRIPTION
            "Information regarding each virtual Eth interface on a pServer."


        ::=     { pServers 6 }


pServerEthEntry OBJECT-TYPE
    SYNTAX      PServerEthEntry
    MAX-ACCESS  not-accessible
    STATUS      current
    DESCRIPTION
            "Information specific to each cBlade Eth in the PAN."

    INDEX       { lPanIndex, pServerIndex, pServerEthIndex }
        ::=     { pServerEthTable 1 }

PServerEthEntry ::=
    SEQUENCE {
        pServerEthIndex
            Integer32,
        pServerEthPServerIndex
            Integer32,
        pServerEthLPanIndex
            Integer32,
        pServerEthName
            DisplayString,
        pServerEthMACAddressOctets
            PhysAddress,
        pServerEthMACAddressString
            DisplayString,
        pServerEthRateLimit
            Integer32
    }


pServerEthIndex OBJECT-TYPE
    SYNTAX      Integer32 (1..2147483647)
    MAX-ACCESS  read-only
    STATUS      current
    DESCRIPTION
            "An integer uniquely identifying this interface within the
            pServer."

        ::=     { pServerEthEntry 1 }


pServerEthPServerIndex OBJECT-TYPE
    SYNTAX      Integer32 (1..2147483647)
    MAX-ACCESS  read-only
    STATUS      current
    DESCRIPTION
            "An integer value identifying the pServerIndex of the
            pServer that hosts this interface."

        ::=     { pServerEthEntry 2 }


pServerEthLPanIndex OBJECT-TYPE
    SYNTAX      Integer32 (1..2147483647)
    MAX-ACCESS  read-only
    STATUS      current
    DESCRIPTION
            "An integer value identifying the lPanIndex value of the
            LPAN that hosts this interface."

        ::=     { pServerEthEntry 3 }


pServerEthName OBJECT-TYPE
    SYNTAX      DisplayString
    MAX-ACCESS  read-only
    STATUS      current
    DESCRIPTION
            "A textual string identifying the network interface."

        ::=     { pServerEthEntry 4 }


pServerEthMACAddressOctets OBJECT-TYPE
    SYNTAX      PhysAddress
    MAX-ACCESS  read-only
    STATUS      current
    DESCRIPTION
            "An encoding of the eth MAC address."

        ::=     { pServerEthEntry 5 }


pServerEthMACAddressString OBJECT-TYPE
    SYNTAX      DisplayString
    MAX-ACCESS  read-only
    STATUS      current
    DESCRIPTION
            "A human readable string representing the eth MAC address
             in the form: '6E:4A:1F:00:01:06'."

        ::=     { pServerEthEntry 6 }


pServerEthRateLimit OBJECT-TYPE
    SYNTAX      Integer32
    MAX-ACCESS  read-only
    STATUS      current
    DESCRIPTION
            "The configured rate limit for the pServer Eth in Mbps.
            0 indicates unlimited."

        ::=     { pServerEthEntry 7 }



pServerEthStatsTable   OBJECT-TYPE
    SYNTAX      SEQUENCE OF PServerEthStatsEntry
    MAX-ACCESS  not-accessible
    STATUS      current
    DESCRIPTION
            "A list of interface statisitcs for each interface in the
            pServer."

        ::=     { pServers 7 }


pServerEthStatsEntry OBJECT-TYPE
    SYNTAX      PServerEthStatsEntry
    MAX-ACCESS  not-accessible
    STATUS      current
    DESCRIPTION
            "Eth statisitcs for each interface in the pServer."

    INDEX       { lPanIndex, pServerIndex, pServerEthIndex }
        ::=     { pServerEthStatsTable 1 }


PServerEthStatsEntry ::=
    SEQUENCE {
        pServerEthStatsInBytes
            Counter32,
        pServerEthStatsInPackets
            Counter32,
        pServerEthStatsInErrs
            Counter32,
        pServerEthStatsInDrops
            Counter32,
        pServerEthStatsInOverrun
            Counter32,
        pServerEthStatsInMulticast
            Counter32,
        pServerEthStatsOutBytes
            Counter32,
        pServerEthStatsOutPackets
            Counter32,
        pServerEthStatsOutErrs
            Counter32,
        pServerEthStatsOutDrops
            Counter32,
        pServerEthStatsOutOverrun
            Counter32,
        pServerEthStatsOutCollisions
            Counter32,
        pServerEthStatsOutCarrierDctFail
            Counter32,
        pServerEthStatsOutCompressed
            Counter32,
        pServerEthStatsOperStatus
            InterfaceOperStatus
    }


pServerEthStatsInBytes OBJECT-TYPE
    SYNTAX      Counter32
    MAX-ACCESS  read-only
    STATUS      current
    DESCRIPTION
            "The number of bytes received on this interface since interface
            reset"

        ::=     { pServerEthStatsEntry 1 }


pServerEthStatsInPackets OBJECT-TYPE
    SYNTAX      Counter32
    MAX-ACCESS  read-only
    STATUS      current
    DESCRIPTION
            "The number of packets received on this interface since interface
            reset"

        ::=     { pServerEthStatsEntry 2 }


pServerEthStatsInErrs OBJECT-TYPE
    SYNTAX      Counter32
    MAX-ACCESS  read-only
    STATUS      current
    DESCRIPTION
            "The number of errors received on this interface since interface
            reset"

        ::=     { pServerEthStatsEntry 3 }


pServerEthStatsInDrops OBJECT-TYPE
    SYNTAX      Counter32
    MAX-ACCESS  read-only
    STATUS      current
    DESCRIPTION
            "The number of dropped incoming packets on this interface since
            interface reset."

        ::=     { pServerEthStatsEntry 4 }


pServerEthStatsInOverrun OBJECT-TYPE
    SYNTAX      Counter32
    MAX-ACCESS  read-only
    STATUS      current
    DESCRIPTION
            "The number of overrun incoming packets on this interface since
            interface reset."

        ::=     { pServerEthStatsEntry 5 }


pServerEthStatsInMulticast OBJECT-TYPE
    SYNTAX      Counter32
    MAX-ACCESS  read-only
    STATUS      current
    DESCRIPTION
            "The number of multicast packets received on this interface since
            interface reset."

        ::=     { pServerEthStatsEntry 6 }


pServerEthStatsOutBytes OBJECT-TYPE
    SYNTAX      Counter32
    MAX-ACCESS  read-only
    STATUS      current
    DESCRIPTION
            "The number of bytes transmitted from this interface since
            interface reset."

        ::=     { pServerEthStatsEntry 7 }


pServerEthStatsOutPackets OBJECT-TYPE
    SYNTAX      Counter32
    MAX-ACCESS  read-only
    STATUS      current
    DESCRIPTION
            "The number of packets transmitted from this interface since
            interface reset."

        ::=     { pServerEthStatsEntry 8 }


pServerEthStatsOutErrs OBJECT-TYPE
    SYNTAX      Counter32
    MAX-ACCESS  read-only
    STATUS      current
    DESCRIPTION
            "The number of errors encountered while transmitting from this
            interface since interface reset."

        ::=     { pServerEthStatsEntry 9 }


pServerEthStatsOutDrops OBJECT-TYPE
    SYNTAX      Counter32
    MAX-ACCESS  read-only
    STATUS      current
    DESCRIPTION
            "The number of dropped packets intended for transmission from this
            interface since interface reset."

        ::=     { pServerEthStatsEntry 10 }


pServerEthStatsOutOverrun OBJECT-TYPE
    SYNTAX      Counter32
    MAX-ACCESS  read-only
    STATUS      current
    DESCRIPTION
            "The number of overrun packets intended for transmission from this
            interface since interface reset."

        ::=     { pServerEthStatsEntry 11 }


pServerEthStatsOutCollisions OBJECT-TYPE
    SYNTAX      Counter32
    MAX-ACCESS  read-only
    STATUS      current
    DESCRIPTION
            "The number of collisions detetced while transmitting from this
            interface since interface reset."

        ::=     { pServerEthStatsEntry 12 }


pServerEthStatsOutCarrierDctFail OBJECT-TYPE
    SYNTAX      Counter32
    MAX-ACCESS  read-only
    STATUS      current
    DESCRIPTION
            "The number of carrier detect failures detetced while transmitting
            from this interface since interface reset."

        ::=     { pServerEthStatsEntry 13 }


pServerEthStatsOutCompressed OBJECT-TYPE
    SYNTAX      Counter32
    MAX-ACCESS  read-only
    STATUS      current
    DESCRIPTION
            "The number of compressed packets transmitted from this interface
            since interface reset."

        ::=     { pServerEthStatsEntry 14 }


pServerEthStatsOperStatus OBJECT-TYPE
    SYNTAX      InterfaceOperStatus
    MAX-ACCESS  read-only
    STATUS      current
    DESCRIPTION
            "The current operational state of the interface."

        ::=     { pServerEthStatsEntry 15 }


-- table of IP address information per pServer Eth

pServerEthIpTable     OBJECT-TYPE
    SYNTAX      SEQUENCE OF PServerEthIpEntry
    MAX-ACCESS  not-accessible
    STATUS      current
    DESCRIPTION
            "A list of IP addresses, broadcast addresses, and nework masks
            configured on each pServer Eth interface."

        ::=     { pServers 8 }


pServerEthIpEntry     OBJECT-TYPE
    SYNTAX      PServerEthIpEntry
    MAX-ACCESS  not-accessible
    STATUS      current
    DESCRIPTION
            "the current IP address, broadcast address, and network mask
            for a pServer Eth interface or alias."

    INDEX       { lPanIndex, pServerIndex, pServerEthIndex, pServerEthIpAliasName }
        ::=     { pServerEthIpTable 1 }


PServerEthIpEntry ::=
    SEQUENCE {
        pServerEthIpAliasName
            DisplayString,
        pServerEthIpEthIndex
            Integer32,
        pServerEthIpPServerIndex
            Integer32,
        pServerEthIpLPanIndex
            Integer32,
        pServerEthIpAddress
            IpAddress,
        pServerEthIpBroadcast
            IpAddress,
        pServerEthIpMask
            IpAddress
    }


pServerEthIpAliasName OBJECT-TYPE
    SYNTAX      DisplayString (SIZE(0..63))
    MAX-ACCESS  read-only
    STATUS      current
    DESCRIPTION
            "The name of this network interface or alias, i.e. lo, veth31, eht10:1"

        ::=     { pServerEthIpEntry 1 }


pServerEthIpEthIndex OBJECT-TYPE
    SYNTAX      Integer32
    MAX-ACCESS  read-only
    STATUS      current
    DESCRIPTION
            "An integer value identifying the pServerEthIndex of the pServer Eth
            that hosts this IP configuraion."

        ::=     { pServerEthIpEntry 2 }


pServerEthIpPServerIndex OBJECT-TYPE
    SYNTAX      Integer32
    MAX-ACCESS  read-only
    STATUS      current
    DESCRIPTION
            "An integer value identifying the pServerIndex of the pServer
            that hosts this IP configuraion."

        ::=     { pServerEthIpEntry 3 }


pServerEthIpLPanIndex OBJECT-TYPE
    SYNTAX      Integer32
    MAX-ACCESS  read-only
    STATUS      current
    DESCRIPTION
            "An integer value identifying the lpanIndex of the LPAN
            that hosts this IP configuraion."

        ::=     { pServerEthIpEntry 4 }


pServerEthIpAddress OBJECT-TYPE
    SYNTAX      IpAddress
    MAX-ACCESS  read-only
    STATUS      current
    DESCRIPTION
            "The IP address configured on this pServer eth (or alias)"

        ::=     { pServerEthIpEntry 5 }


pServerEthIpBroadcast OBJECT-TYPE
    SYNTAX      IpAddress
    MAX-ACCESS  read-only
    STATUS      current
    DESCRIPTION
            "The broadcast address configured on this pServer eth (or alias)"

        ::=     { pServerEthIpEntry 6 }


pServerEthIpMask OBJECT-TYPE
    SYNTAX      IpAddress
    MAX-ACCESS  read-only
    STATUS      current
    DESCRIPTION
            "The network mask configured on this pServer eth (or alias)"

        ::=     { pServerEthIpEntry 7 }





-- pServer Controls

pServerControlTable   OBJECT-TYPE
    SYNTAX      SEQUENCE OF PServerControlEntry
    MAX-ACCESS  not-accessible
    STATUS      current
    DESCRIPTION
            "A list of pServer controls for each pServer."

        ::=     { pServers 9 }


pServerControlEntry OBJECT-TYPE
    SYNTAX      PServerControlEntry
    MAX-ACCESS  not-accessible
    STATUS      current
    DESCRIPTION
            "Controls for each pServer."

    INDEX       { lPanIndex, pServerIndex }
        ::=     { pServerControlTable 1 }


PServerControlEntry ::=
    SEQUENCE {
        pServerControlPowerUp
            Integer32,
        pServerControlPowerDown
            Integer32,
        pServerControlColdReset
            Integer32,
        pServerControlWarmReset
            Integer32,
        pServerControlNmi
            Integer32,
        pServerBoot
            Integer32,
        pServerShutdown
            Integer32,
        pServerForceShutdown
            Integer32,
        pServerReboot
            Integer32,
        pServerForceReboot
            Integer32
    }

pServerControlPowerUp OBJECT-TYPE
    SYNTAX      Integer32
    MAX-ACCESS  read-write
    STATUS      current
    DESCRIPTION
            "This object is deprecated as of PAN Manager release 4.0.
            This control is available via the pBladeControlTable"

        ::=     { pServerControlEntry 1 }


pServerControlPowerDown OBJECT-TYPE
    SYNTAX      Integer32
    MAX-ACCESS  read-write
    STATUS      current
    DESCRIPTION
            "This object is deprecated as of PAN Manager release 4.0.
            This control is available via the pBladeControlTable"

        ::=     { pServerControlEntry 2 }


pServerControlColdReset OBJECT-TYPE
    SYNTAX      Integer32
    MAX-ACCESS  read-write
    STATUS      current
    DESCRIPTION
            "This object is deprecated as of PAN Manager release 4.0.
            This control is available via the pBladeControlTable"

        ::=     { pServerControlEntry 3 }


pServerControlWarmReset OBJECT-TYPE
    SYNTAX      Integer32
    MAX-ACCESS  read-write
    STATUS      current
    DESCRIPTION
            "This object is deprecated as of PAN Manager release 4.0.
            This control is available via the pBladeControlTable"

        ::=     { pServerControlEntry 4 }


pServerControlNmi OBJECT-TYPE
    SYNTAX      Integer32
    MAX-ACCESS  read-write
    STATUS      current
    DESCRIPTION
            "This object is deprecated as of PAN Manager release 4.0.
            This control is available via the pBladeControlTable"

        ::=     { pServerControlEntry 5 }


pServerBoot OBJECT-TYPE
    SYNTAX      Integer32
    MAX-ACCESS  read-write
    STATUS      current
    DESCRIPTION
            "When set to 1, initiates a boot operation on this pServer.
            When read, returns 0."

        ::=     { pServerControlEntry 6 }


pServerShutdown OBJECT-TYPE
    SYNTAX      Integer32
    MAX-ACCESS  read-write
    STATUS      current
    DESCRIPTION
            "When set to 1, initiates a shutdown operation on this pServer.
            When read, returns 0."

        ::=     { pServerControlEntry 7 }


pServerForceShutdown OBJECT-TYPE
    SYNTAX      Integer32
    MAX-ACCESS  read-write
    STATUS      current
    DESCRIPTION
            "When set to 1, initiates a force shutdown operation on this pServer.
            When read, returns 0."

        ::=     { pServerControlEntry 8 }


pServerReboot OBJECT-TYPE
    SYNTAX      Integer32
    MAX-ACCESS  read-write
    STATUS      current
    DESCRIPTION
            "When set to 1, initiates a reboot operation on this pServer.
            When read, returns 0."

        ::=     { pServerControlEntry 9 }


pServerForceReboot OBJECT-TYPE
    SYNTAX      Integer32
    MAX-ACCESS  read-write
    STATUS      current
    DESCRIPTION
            "When set to 1, initiates a force reboot operation on this pServer.
            When read, returns 0."

        ::=     { pServerControlEntry 10 }

-- applications group
-- contains information and controls for applications under PAN Manager
-- control.

applications OBJECT IDENTIFIER ::= { lPans 4 }


applicationTable   OBJECT-TYPE
    SYNTAX      SEQUENCE OF ApplicationEntry
    MAX-ACCESS  not-accessible
    STATUS      current
    DESCRIPTION
            "A list of Application entries containing information about each
            application configured for PAN Manager control."

        ::=     { applications 1 }


applicationEntry OBJECT-TYPE
    SYNTAX      ApplicationEntry
    MAX-ACCESS  not-accessible
    STATUS      current
    DESCRIPTION
            "Information regarding each application."

    INDEX       { lPanIndex, applicationIndex }
        ::=     { applicationTable 1 }


ApplicationEntry ::=
    SEQUENCE {
        applicationIndex
            Integer32,
        applicationLPanIndex
            Integer32,
        applicationName
            DisplayString,
        applicationDescription
            DisplayString,
        applicationStatus
            DisplayString,
        applicationHealth
            DisplayString,
        appCurrentPServerIndex
            Integer32,
        appPrimaryPServerIndex
            Integer32
    }

applicationIndex OBJECT-TYPE
    SYNTAX      Integer32 (1..2147483647)
    MAX-ACCESS  read-only
    STATUS      current
    DESCRIPTION
            "An integer value uniquely identifying the application within the
            LPAN."

        ::=     { applicationEntry 1 }


applicationLPanIndex OBJECT-TYPE
    SYNTAX      Integer32 (1..2147483647)
    MAX-ACCESS  read-only
    STATUS      current
    DESCRIPTION
            "An integer value identifying the lPanIndex value of the
            LPAN that hosts this application."

        ::=     { applicationEntry 2 }


applicationName OBJECT-TYPE
    SYNTAX      DisplayString
    MAX-ACCESS  read-only
    STATUS      current
    DESCRIPTION
            "A textual string identifying the application."

        ::=     { applicationEntry 3 }


applicationDescription OBJECT-TYPE
    SYNTAX      DisplayString
    MAX-ACCESS  read-only
    STATUS      current
    DESCRIPTION
            "A textual string describing the application."

        ::=     { applicationEntry 4 }


applicationStatus OBJECT-TYPE
    SYNTAX      DisplayString
    MAX-ACCESS  read-only
    STATUS      current
    DESCRIPTION
            "A textual string describing the operational status of the
            application."

        ::=     { applicationEntry 5 }


applicationHealth OBJECT-TYPE
    SYNTAX      DisplayString
    MAX-ACCESS  read-only
    STATUS      current
    DESCRIPTION
            "This object is deprecated"

        ::=     { applicationEntry 6 }


appCurrentPServerIndex OBJECT-TYPE
    SYNTAX      Integer32
    MAX-ACCESS  read-only
    STATUS      current
    DESCRIPTION
            "An integer value identifying the pServerIndex value of the
            pServer currently hosting this application."

        ::=     { applicationEntry 7 }


appPrimaryPServerIndex OBJECT-TYPE
    SYNTAX      Integer32
    MAX-ACCESS  read-only
    STATUS      current
    DESCRIPTION
            "An integer value identifying the pServerIndex value of the
            pServer configured as the application's primary pServer."

        ::=     { applicationEntry 8 }


applicationControlTable   OBJECT-TYPE
    SYNTAX      SEQUENCE OF ApplicationControlEntry
    MAX-ACCESS  not-accessible
    STATUS      current
    DESCRIPTION
            "A list of application entries containing controls for each
            application configured for PAN Manager control."

        ::=     { applications 2 }


applicationControlEntry OBJECT-TYPE
    SYNTAX      ApplicationControlEntry
    MAX-ACCESS  not-accessible
    STATUS      current
    DESCRIPTION
            "Controls for each application."

    INDEX       { lPanIndex, applicationIndex }
        ::=     { applicationControlTable 1 }


ApplicationControlEntry ::=
    SEQUENCE {
        applicationStart
            Integer32,
        applicationStop
            Integer32,
        applicationForceStop
            Integer32,
        applicationMove
            Integer32
    }


applicationStart OBJECT-TYPE
    SYNTAX      Integer32
    MAX-ACCESS      read-write
    STATUS      current
    DESCRIPTION
            "When set to 1, initiates a start operation on this application.
            When read, returns 0."

        ::=     { applicationControlEntry 1 }


applicationStop OBJECT-TYPE
    SYNTAX      Integer32
    MAX-ACCESS      read-write
    STATUS      current
    DESCRIPTION
            "When set to 1, initiates a stop operation on this
            application. When read, returns 0."

        ::=     { applicationControlEntry 2 }


applicationForceStop OBJECT-TYPE
    SYNTAX      Integer32
    MAX-ACCESS      read-write
    STATUS      current
    DESCRIPTION
            "When set to 1, initiates a force stop operation on this
            application. When read, returns 0."

        ::=     { applicationControlEntry 3 }


applicationMove OBJECT-TYPE
    SYNTAX      Integer32
    MAX-ACCESS      read-write
    STATUS      current
    DESCRIPTION
            "When set to 1, initiates a move operation on this
            application. When read, returns 0."

        ::=     { applicationControlEntry 4 }


-- configured failover policies
applicationFOPTable   OBJECT-TYPE
    SYNTAX      SEQUENCE OF ApplicationFOPEntry
    MAX-ACCESS  not-accessible
    STATUS      current
    DESCRIPTION
            "A list of Application failover policy assignments."

        ::=     { applications 3 }


applicationFOPEntry OBJECT-TYPE
    SYNTAX      ApplicationFOPEntry
    MAX-ACCESS  not-accessible
    STATUS      current
    DESCRIPTION
            "Indicates a failover policy to application assignment by
            identifying failoverPolicyIndex of the failover policy
            assigned to the application"

    INDEX       { lPanIndex, applicationIndex, applicationFOPIndex }
        ::=     { applicationFOPTable 1 }


ApplicationFOPEntry ::=
    SEQUENCE {
        applicationFOPIndex
            Integer32
    }


applicationFOPIndex OBJECT-TYPE
    SYNTAX      Integer32 (1..2147483647)
    MAX-ACCESS  read-only
    STATUS      current
    DESCRIPTION
            "An integer value identifying the failoverPolicyIndex of the
            failover policy mapped to the application."

        ::=     { applicationFOPEntry 1 }

-- configured health monitors
applicationHMONTable   OBJECT-TYPE
    SYNTAX      SEQUENCE OF ApplicationHMONEntry
    MAX-ACCESS  not-accessible
    STATUS      current
    DESCRIPTION
            "A list of Application health monitor assignments."

        ::=     { applications 4 }


applicationHMONEntry OBJECT-TYPE
    SYNTAX      ApplicationHMONEntry
    MAX-ACCESS  not-accessible
    STATUS      current
    DESCRIPTION
            "Indicates a health monitor to application assignment by
            identifying healthMonitorIndex of the health monitor
            assigned to the application"

    INDEX       { lPanIndex, applicationIndex, applicationHMONIndex }
        ::=     { applicationHMONTable 1 }


ApplicationHMONEntry ::=
    SEQUENCE {
        applicationHMONIndex
            Integer32
    }


applicationHMONIndex OBJECT-TYPE
    SYNTAX      Integer32 (1..2147483647)
    MAX-ACCESS  read-only
    STATUS      current
    DESCRIPTION
            "An integer value identifying the healthMonitorIndex of the
            health monitor mapped to the application."

        ::=     { applicationHMONEntry 1 }


-- configured executable resources
applicationExResTable   OBJECT-TYPE
    SYNTAX      SEQUENCE OF ApplicationExResEntry
    MAX-ACCESS  not-accessible
    STATUS      current
    DESCRIPTION
            "A list of Application executable resource assignments."

        ::=     { applications 5 }


applicationExResEntry OBJECT-TYPE
    SYNTAX      ApplicationExResEntry
    MAX-ACCESS  not-accessible
    STATUS      current
    DESCRIPTION
            "Indicates a executable resource to application assignment by
            identifying executableResourceIndex of the executable resource
            assigned to the application"

    INDEX       { lPanIndex, applicationIndex, applicationExResIndex }
        ::=     { applicationExResTable 1 }


ApplicationExResEntry ::=
    SEQUENCE {
        applicationExResIndex
            Integer32
    }


applicationExResIndex OBJECT-TYPE
    SYNTAX      Integer32 (1..2147483647)
    MAX-ACCESS  read-only
    STATUS      current
    DESCRIPTION
            "An integer value identifying the executableResourceIndex of the
            executable resource mapped to the application."

        ::=     { applicationExResEntry 1 }


-- configured SCSI disk resources
applicationSCSIResTable   OBJECT-TYPE
    SYNTAX      SEQUENCE OF ApplicationSCSIResEntry
    MAX-ACCESS  not-accessible
    STATUS      current
    DESCRIPTION
            "A list of Application SCSI disk resource assignments."

        ::=     { applications 6 }


applicationSCSIResEntry OBJECT-TYPE
    SYNTAX      ApplicationSCSIResEntry
    MAX-ACCESS  not-accessible
    STATUS      current
    DESCRIPTION
            "Indicates a SCSIRes disk resource to application assignment by
            identifying scsiDiskResourceIndex of the SCSI disk resource
            assigned to the application"

    INDEX       { lPanIndex, applicationIndex, applicationSCSIResIndex }
        ::=     { applicationSCSIResTable 1 }


ApplicationSCSIResEntry ::=
    SEQUENCE {
        applicationSCSIResIndex
            Integer32
    }


applicationSCSIResIndex OBJECT-TYPE
    SYNTAX      Integer32 (1..2147483647)
    MAX-ACCESS  read-only
    STATUS      current
    DESCRIPTION
            "An integer value identifying the scsiDiskResourceIndex of the
            SCSI disk resource mapped to the application."

        ::=     { applicationSCSIResEntry 1 }


-- configured NFS resources
applicationNFSResTable   OBJECT-TYPE
    SYNTAX      SEQUENCE OF ApplicationNFSResEntry
    MAX-ACCESS  not-accessible
    STATUS      current
    DESCRIPTION
            "A list of Application NFS resource assignments."

        ::=     { applications 7 }


applicationNFSResEntry OBJECT-TYPE
    SYNTAX      ApplicationNFSResEntry
    MAX-ACCESS  not-accessible
    STATUS      current
    DESCRIPTION
            "Indicates an NFS resource to application assignment by
            identifying nfsResourceIndex of the NFS resource
            assigned to the application"

    INDEX       { lPanIndex, applicationIndex, applicationNFSResIndex }
        ::=     { applicationNFSResTable 1 }


ApplicationNFSResEntry ::=
    SEQUENCE {
        applicationNFSResIndex
            Integer32
    }


applicationNFSResIndex OBJECT-TYPE
    SYNTAX      Integer32 (1..2147483647)
    MAX-ACCESS  read-only
    STATUS      current
    DESCRIPTION
            "An integer value identifying the nfsResourceIndex of the
            NFS resource mapped to the application."

        ::=     { applicationNFSResEntry 1 }


-- configured network resources
applicationNetResTable   OBJECT-TYPE
    SYNTAX      SEQUENCE OF ApplicationNetResEntry
    MAX-ACCESS  not-accessible
    STATUS      current
    DESCRIPTION
            "A list of Application Network resource assignments."

        ::=     { applications 8 }


applicationNetResEntry OBJECT-TYPE
    SYNTAX      ApplicationNetResEntry
    MAX-ACCESS  not-accessible
    STATUS      current
    DESCRIPTION
            "Indicates a Network resource to application assignment by
            identifying networkResourceIndex of the Network resource
            assigned to the application"

    INDEX       { lPanIndex, applicationIndex, applicationNetResIndex }
        ::=     { applicationNetResTable 1 }


ApplicationNetResEntry ::=
    SEQUENCE {
        applicationNetResIndex
            Integer32
    }


applicationNetResIndex OBJECT-TYPE
    SYNTAX      Integer32 (1..2147483647)
    MAX-ACCESS  read-only
    STATUS      current
    DESCRIPTION
            "An integer value identifying the networkResourceIndex of the
            executable resource mapped to the application."

        ::=     { applicationNetResEntry 1 }



loadBalancers OBJECT IDENTIFIER ::= { lPans 5 }

-- load balancers
loadBalancerTable   OBJECT-TYPE
    SYNTAX      SEQUENCE OF LoadBalancerEntry
    MAX-ACCESS  not-accessible
    STATUS      current
    DESCRIPTION
            "A list of load balancer entries containing information about each
            load balancer configured for PAN Manager control."

        ::=     { loadBalancers 1 }


loadBalancerEntry OBJECT-TYPE
    SYNTAX      LoadBalancerEntry
    MAX-ACCESS  not-accessible
    STATUS      current
    DESCRIPTION
            "Information regarding each load balancer."

    INDEX       { lPanIndex, loadBalancerIndex }
        ::=     { loadBalancerTable 1 }


LoadBalancerEntry ::=
    SEQUENCE {
        loadBalancerIndex
            Integer32,
        loadBalancerLPanIndex
            Integer32,
        loadBalancerName
            DisplayString,
        loadBalancerDescription
            DisplayString,
        loadBalancerStatus
            DisplayString,
        lbCurrentPServerIndex
            Integer32,
        lbPrimaryPServerIndex
            Integer32,
        loadBalancerAutoStart
            TruthValue
    }

loadBalancerIndex OBJECT-TYPE
    SYNTAX      Integer32 (1..2147483647)
    MAX-ACCESS  read-only
    STATUS      current
    DESCRIPTION
            "An integer value uniquely identifying the load balancer within the
            LPAN."

        ::=     { loadBalancerEntry 1 }

loadBalancerLPanIndex OBJECT-TYPE
    SYNTAX      Integer32 (1..2147483647)
    MAX-ACCESS  read-only
    STATUS      current
    DESCRIPTION
            "An integer value identifying the lPanIndex value of the
            LPAN that hosts this loadBalancer."

        ::=     { loadBalancerEntry 2 }


loadBalancerName OBJECT-TYPE
    SYNTAX      DisplayString
    MAX-ACCESS  read-only
    STATUS      current
    DESCRIPTION
            "A textual string identifying the load balancer."

        ::=     { loadBalancerEntry 3 }


loadBalancerDescription OBJECT-TYPE
    SYNTAX      DisplayString
    MAX-ACCESS  read-only
    STATUS      current
    DESCRIPTION
            "A textual string describing the load balancer."

        ::=     { loadBalancerEntry 4 }


loadBalancerStatus OBJECT-TYPE
    SYNTAX      DisplayString
    MAX-ACCESS  read-only
    STATUS      current
    DESCRIPTION
            "A textual string describing the operational status of the
            loadBalancer."

        ::=     { loadBalancerEntry 5 }


lbCurrentPServerIndex OBJECT-TYPE
    SYNTAX      Integer32 (1..2147483647)
    MAX-ACCESS  read-only
    STATUS      current
    DESCRIPTION
            "An integer value identifying the pServerIndex value of the
            pServer currently hosting this load balancer."

        ::=     { loadBalancerEntry 6 }


lbPrimaryPServerIndex OBJECT-TYPE
    SYNTAX      Integer32 (1..2147483647)
    MAX-ACCESS  read-only
    STATUS      current
    DESCRIPTION
            "An integer value identifying the pServerIndex value of the
            pServer configured as the load balancer's primare pServer."

        ::=     { loadBalancerEntry 7 }


loadBalancerAutoStart OBJECT-TYPE
    SYNTAX      TruthValue
    MAX-ACCESS  read-only
    STATUS      current
    DESCRIPTION
            "A boolean value indicating whether or not the load balancer
            is configured for auto-start."

        ::=     { loadBalancerEntry 8 }



loadBalancerControlTable   OBJECT-TYPE
    SYNTAX      SEQUENCE OF LoadBalancerControlEntry
    MAX-ACCESS  not-accessible
    STATUS      current
    DESCRIPTION
            "A list of load balancer entries containing controls for each
            load balancer configured for PAN Manager control."

        ::=     { loadBalancers 2 }


loadBalancerControlEntry OBJECT-TYPE
    SYNTAX      LoadBalancerControlEntry
    MAX-ACCESS  not-accessible
    STATUS      current
    DESCRIPTION
            "Controls for each load balancer."

    INDEX       { lPanIndex, loadBalancerIndex }
        ::=     { loadBalancerControlTable 1 }


LoadBalancerControlEntry ::=
    SEQUENCE {
        loadBalancerStart
            Integer32,
        loadBalancerStop
            Integer32,
        loadBalancerForceStop
            Integer32,
        loadBalancerMove
            Integer32
    }


loadBalancerStart OBJECT-TYPE
    SYNTAX      Integer32
    MAX-ACCESS      read-write
    STATUS      current
    DESCRIPTION
            "When set to 1, initiates a start operation on this load balancer.
            When read, returns 0."

        ::=     { loadBalancerControlEntry 1 }


loadBalancerStop OBJECT-TYPE
    SYNTAX      Integer32
    MAX-ACCESS      read-write
    STATUS      current
    DESCRIPTION
            "When set to 1, initiates a stop operation on this
            load balancer. When read, returns 0."

        ::=     { loadBalancerControlEntry 2 }


loadBalancerForceStop OBJECT-TYPE
    SYNTAX      Integer32
    MAX-ACCESS      read-write
    STATUS      current
    DESCRIPTION
            "When set to 1, initiates a force stop operation on this
            load balancer. When read, returns 0."

        ::=     { loadBalancerControlEntry 3 }


loadBalancerMove OBJECT-TYPE
    SYNTAX      Integer32
    MAX-ACCESS      read-write
    STATUS      current
    DESCRIPTION
            "When set to 1, initiates a move operation on this
            load balancer. When read, returns 0."

        ::=     { loadBalancerControlEntry 4 }


ProtocolType ::= TEXTUAL-CONVENTION
    STATUS      current
    DESCRIPTION
            "Describes the protocol for load balancer connections."
    SYNTAX INTEGER {
        tcp(1),
        udp(2),
        undefined(999)
    }

SchedulePolicyType ::= TEXTUAL-CONVENTION
    STATUS      current
    DESCRIPTION
            "Describes schedule policies for load balancer connections."
    SYNTAX INTEGER {
        round-robin(1),             -- distribute jobs equally among available pServers.
        weighted-round-robin(2),    -- assign relatively more jobs to pServers with larger capacity.
        least-connection(3),        -- assign relatively more jobs to pServers with fewer scheduled jobs.
        weighted-least-connected(4),-- assign relatively more jobs to pServers with less scheduled jobs relative to their capacity.
        undefined(999)
    }


loadBalancerConnectionTable   OBJECT-TYPE
    SYNTAX      SEQUENCE OF LoadBalancerConnectionEntry
    MAX-ACCESS  not-accessible
    STATUS      current
    DESCRIPTION
            "A list of configured connections to the load balancer service."

        ::=     { loadBalancers 3 }


loadBalancerConnectionEntry OBJECT-TYPE
    SYNTAX      LoadBalancerConnectionEntry
    MAX-ACCESS  not-accessible
    STATUS      current
    DESCRIPTION
            "Attributes of each load balancer connection"

    INDEX       { lPanIndex, loadBalancerIndex, loadBalancerConnectionIndex }
        ::=     { loadBalancerConnectionTable 1 }


LoadBalancerConnectionEntry ::=
    SEQUENCE {
        loadBalancerConnectionIndex
            Integer32,
        loadBalancerConnectionProto
            ProtocolType,
        loadBalancerConnectionPort
            Integer32,
        lbConnectionStartSchedPolicy
            SchedulePolicyType,
        loadBalancerPersistConnection
            TruthValue
    }


loadBalancerConnectionIndex OBJECT-TYPE
    SYNTAX      Integer32 (1..2147483647)
    MAX-ACCESS  read-only
    STATUS      current
    DESCRIPTION
            "An integer value uniquely identifying the connection within the
            load balancer."

        ::=     { loadBalancerConnectionEntry 1 }


loadBalancerConnectionProto OBJECT-TYPE
    SYNTAX      ProtocolType
    MAX-ACCESS  read-only
    STATUS      current
    DESCRIPTION
            "Indicates the connection protocol; TCP or UDP."

        ::=     { loadBalancerConnectionEntry 2 }


loadBalancerConnectionPort OBJECT-TYPE
    SYNTAX      Integer32
    MAX-ACCESS  read-only
    STATUS      current
    DESCRIPTION
            "Indicates the connection port."

        ::=     { loadBalancerConnectionEntry 3 }


lbConnectionStartSchedPolicy OBJECT-TYPE
    SYNTAX      SchedulePolicyType
    MAX-ACCESS  read-only
    STATUS      current
    DESCRIPTION
            "Indicates the scheduling policy for the connection.
            - rr-round robin (default): distribute jobs equally among available pServers.
            - wrr-weighted-round-robin: assign relatively more jobs to pServers with larger
                    capacity.
            - lc-least-connection-assign: relatively more jobs to pServers with fewer
                    scheduled jobs.
            - wlc-weighted-least-connected: assign relatively more jobs to pServers with less
                    scheduled jobs relative to their capacity."

        ::=     { loadBalancerConnectionEntry 4 }


loadBalancerPersistConnection OBJECT-TYPE
    SYNTAX      TruthValue
    MAX-ACCESS  read-only
    STATUS      current
    DESCRIPTION
            "Indicates the whether or not established connections from clients should
            always be serviced by the same load balancer member."

        ::=     { loadBalancerConnectionEntry 5 }


loadBalancerMemberTable   OBJECT-TYPE
    SYNTAX      SEQUENCE OF LoadBalancerMemberEntry
    MAX-ACCESS  not-accessible
    STATUS      current
    DESCRIPTION
            "A list of applications that are members of the load balancer
            service."

        ::=     { loadBalancers 4 }


loadBalancerMemberEntry OBJECT-TYPE
    SYNTAX      LoadBalancerMemberEntry
    MAX-ACCESS  not-accessible
    STATUS      current
    DESCRIPTION
            "Attributes of each application that is a member of the load
            balancer service."

    INDEX       { lPanIndex, loadBalancerIndex, loadBalancerMemberIndex }
        ::=     { loadBalancerMemberTable 1 }


LoadBalancerMemberEntry ::=
    SEQUENCE {
        loadBalancerMemberIndex
            Integer32,
        loadBalancerMemberWeight
            Integer32,
        lbMemberStartWithService
            TruthValue
    }


loadBalancerMemberIndex OBJECT-TYPE
    SYNTAX      Integer32 (1..2147483647)
    MAX-ACCESS  read-only
    STATUS      current
    DESCRIPTION
            "An integer value identifying the applicationIndex value of the
            application that is a member of this load balancer service."

        ::=     { loadBalancerMemberEntry 1 }


loadBalancerMemberWeight OBJECT-TYPE
    SYNTAX      Integer32
    MAX-ACCESS  read-only
    STATUS      current
    DESCRIPTION
            "An integer value identifying the weight criteria for the member,
            a member with weight 2 will handle twice the load as a member of
            weight 1."

        ::=     { loadBalancerMemberEntry 2 }


lbMemberStartWithService OBJECT-TYPE
    SYNTAX      TruthValue
    MAX-ACCESS  read-only
    STATUS      current
    DESCRIPTION
            "Indicates whether or not this member is configured to start when
            the load balancer service is started."

        ::=     { loadBalancerMemberEntry 3 }

-- configured failover policies
loadBalancerFOPTable   OBJECT-TYPE
    SYNTAX      SEQUENCE OF LoadBalancerFOPEntry
    MAX-ACCESS  not-accessible
    STATUS      current
    DESCRIPTION
            "A list of load balancer failover policy assignments."

        ::=     { loadBalancers 5 }


loadBalancerFOPEntry OBJECT-TYPE
    SYNTAX      LoadBalancerFOPEntry
    MAX-ACCESS  not-accessible
    STATUS      current
    DESCRIPTION
            "Indicates a failover policy to load balancer assignment by
            identifying failoverPolicyIndex of the failover policy
            assigned to the load balancer"

    INDEX       { lPanIndex, loadBalancerIndex, loadBalancerFOPIndex }
        ::=     { loadBalancerFOPTable 1 }


LoadBalancerFOPEntry ::=
    SEQUENCE {
        loadBalancerFOPIndex
            Integer32
    }


loadBalancerFOPIndex OBJECT-TYPE
    SYNTAX      Integer32 (1..2147483647)
    MAX-ACCESS  read-only
    STATUS      current
    DESCRIPTION
            "An integer value identifying the failoverPolicyIndex of the
            failover policy mapped to the load balancer."

        ::=     { loadBalancerFOPEntry 1 }

-- configured health monitors
loadBalancerHMONTable   OBJECT-TYPE
    SYNTAX      SEQUENCE OF LoadBalancerHMONEntry
    MAX-ACCESS  not-accessible
    STATUS      current
    DESCRIPTION
            "A list of load balancer health monitor assignments."

        ::=     { loadBalancers 6 }


loadBalancerHMONEntry OBJECT-TYPE
    SYNTAX      LoadBalancerHMONEntry
    MAX-ACCESS  not-accessible
    STATUS      current
    DESCRIPTION
            "Indicates a health monitor to load balancer assignment by
            identifying healthMonitorIndex of the health monitor
            assigned to the load balancer"

    INDEX       { lPanIndex, loadBalancerIndex, loadBalancerHMONIndex }
        ::=     { loadBalancerHMONTable 1 }


LoadBalancerHMONEntry ::=
    SEQUENCE {
        loadBalancerHMONIndex
            Integer32
    }


loadBalancerHMONIndex OBJECT-TYPE
    SYNTAX      Integer32 (1..2147483647)
    MAX-ACCESS  read-only
    STATUS      current
    DESCRIPTION
            "An integer value identifying the healthMonitorIndex of the
            health monitor mapped to the load balancer."

        ::=     { loadBalancerHMONEntry 1 }


-- configured executable resources
loadBalancerExResTable   OBJECT-TYPE
    SYNTAX      SEQUENCE OF LoadBalancerExResEntry
    MAX-ACCESS  not-accessible
    STATUS      current
    DESCRIPTION
            "A list of load balancer executable resource assignments."

        ::=     { loadBalancers 7 }


loadBalancerExResEntry OBJECT-TYPE
    SYNTAX      LoadBalancerExResEntry
    MAX-ACCESS  not-accessible
    STATUS      current
    DESCRIPTION
            "Indicates a executable resource to load balancer assignment by
            identifying executableResourceIndex of the executable resource
            assigned to the load balancer"

    INDEX       { lPanIndex, loadBalancerIndex, loadBalancerExResIndex }
        ::=     { loadBalancerExResTable 1 }


LoadBalancerExResEntry ::=
    SEQUENCE {
        loadBalancerExResIndex
            Integer32
    }


loadBalancerExResIndex OBJECT-TYPE
    SYNTAX      Integer32 (1..2147483647)
    MAX-ACCESS  read-only
    STATUS      current
    DESCRIPTION
            "An integer value identifying the executableResourceIndex of the
            executable resource mapped to the load balancer."

        ::=     { loadBalancerExResEntry 1 }


-- configured SCSI disk resources
loadBalancerSCSIResTable   OBJECT-TYPE
    SYNTAX      SEQUENCE OF LoadBalancerSCSIResEntry
    MAX-ACCESS  not-accessible
    STATUS      current
    DESCRIPTION
            "A list of load balancer SCSI disk resource assignments."

        ::=     { loadBalancers 8 }


loadBalancerSCSIResEntry OBJECT-TYPE
    SYNTAX      LoadBalancerSCSIResEntry
    MAX-ACCESS  not-accessible
    STATUS      current
    DESCRIPTION
            "Indicates a SCSIRes disk resource to load balancer assignment by
            identifying scsiDiskResourceIndex of the SCSI disk resource
            assigned to the load balancer"

    INDEX       { lPanIndex, loadBalancerIndex, loadBalancerSCSIResIndex }
        ::=     { loadBalancerSCSIResTable 1 }


LoadBalancerSCSIResEntry ::=
    SEQUENCE {
        loadBalancerSCSIResIndex
            Integer32
    }


loadBalancerSCSIResIndex OBJECT-TYPE
    SYNTAX      Integer32 (1..2147483647)
    MAX-ACCESS  read-only
    STATUS      current
    DESCRIPTION
            "An integer value identifying the scsiDiskResourceIndex of the
            SCSI disk resource mapped to the load balancer."

        ::=     { loadBalancerSCSIResEntry 1 }


-- configured NFS resources
loadBalancerNFSResTable   OBJECT-TYPE
    SYNTAX      SEQUENCE OF LoadBalancerNFSResEntry
    MAX-ACCESS  not-accessible
    STATUS      current
    DESCRIPTION
            "A list of load balancer NFS resource assignments."

        ::=     { loadBalancers 9 }


loadBalancerNFSResEntry OBJECT-TYPE
    SYNTAX      LoadBalancerNFSResEntry
    MAX-ACCESS  not-accessible
    STATUS      current
    DESCRIPTION
            "Indicates an NFS resource to load balancer assignment by
            identifying nfsResourceIndex of the NFS resource
            assigned to the load balancer"

    INDEX       { lPanIndex, loadBalancerIndex, loadBalancerNFSResIndex }
        ::=     { loadBalancerNFSResTable 1 }


LoadBalancerNFSResEntry ::=
    SEQUENCE {
        loadBalancerNFSResIndex
            Integer32
    }


loadBalancerNFSResIndex OBJECT-TYPE
    SYNTAX      Integer32 (1..2147483647)
    MAX-ACCESS  read-only
    STATUS      current
    DESCRIPTION
            "An integer value identifying the nfsResourceIndex of the
            NFS resource mapped to the load balancer."

        ::=     { loadBalancerNFSResEntry 1 }


-- configured network resources
loadBalancerNetResTable   OBJECT-TYPE
    SYNTAX      SEQUENCE OF LoadBalancerNetResEntry
    MAX-ACCESS  not-accessible
    STATUS      current
    DESCRIPTION
            "A list of load balancer Network resource assignments."

        ::=     { loadBalancers 10 }


loadBalancerNetResEntry OBJECT-TYPE
    SYNTAX      LoadBalancerNetResEntry
    MAX-ACCESS  not-accessible
    STATUS      current
    DESCRIPTION
            "Indicates a Network resource to load balancer assignment by
            identifying networkResourceIndex of the Network resource
            assigned to the load balancer"

    INDEX       { lPanIndex, loadBalancerIndex, loadBalancerNetResIndex }
        ::=     { loadBalancerNetResTable 1 }


LoadBalancerNetResEntry ::=
    SEQUENCE {
        loadBalancerNetResIndex
            Integer32
    }


loadBalancerNetResIndex OBJECT-TYPE
    SYNTAX      Integer32 (1..2147483647)
    MAX-ACCESS  read-only
    STATUS      current
    DESCRIPTION
            "An integer value identifying the networkResourceIndex of the
            executable resource mapped to the load balancer."

        ::=     { loadBalancerNetResEntry 1 }


applicationResources OBJECT IDENTIFIER ::= { lPans 6 }

failoverPolicies OBJECT IDENTIFIER ::= { applicationResources 1 }

FOPSelectionPolicyType ::= TEXTUAL-CONVENTION
    STATUS      current
    DESCRIPTION
            "Describes schedule policies for failover policies."
    SYNTAX INTEGER {
        ordered(1),
        round-robin(2),
        undefined(999)
    }


failoverPolicyTable   OBJECT-TYPE
    SYNTAX      SEQUENCE OF FailoverPolicyEntry
    MAX-ACCESS  not-accessible
    STATUS      current
    DESCRIPTION
            "A list of entries describing failover policies."

        ::=     { failoverPolicies 1 }


failoverPolicyEntry OBJECT-TYPE
    SYNTAX      FailoverPolicyEntry
    MAX-ACCESS  not-accessible
    STATUS      current
    DESCRIPTION
            "A list of attributes describing a failover policy"

    INDEX       { lPanIndex, failoverPolicyIndex }
        ::=     { failoverPolicyTable 1 }


FailoverPolicyEntry ::=
    SEQUENCE {
        failoverPolicyIndex
            Integer32,
        failoverPolicyLPANIndex
            Integer32,
        failoverPolicyName
            DisplayString,
        failoverPolicyDescription
            DisplayString,
        failoverPolicySelectionPolicy
            FOPSelectionPolicyType,
        failoverPolicyAutoFailback
            TruthValue,
        failoverPolicyRebootPServer
            TruthValue
    }


failoverPolicyIndex OBJECT-TYPE
    SYNTAX      Integer32 (1..2147483647)
    MAX-ACCESS  read-only
    STATUS      current
    DESCRIPTION
            "An integer value identifying the failover policy within the
            LPAN."

        ::=     { failoverPolicyEntry 1 }


failoverPolicyLPANIndex OBJECT-TYPE
    SYNTAX      Integer32 (1..2147483647)
    MAX-ACCESS  read-only
    STATUS      current
    DESCRIPTION
            "An integer value identifying the lPanIndex value of the
            LPAN that hosts this failover policy."

        ::=     { failoverPolicyEntry 2 }

failoverPolicyName OBJECT-TYPE
    SYNTAX      DisplayString
    MAX-ACCESS  read-only
    STATUS      current
    DESCRIPTION
            "A textual String identifying the failover policy."

        ::=     { failoverPolicyEntry 3 }


failoverPolicyDescription OBJECT-TYPE
    SYNTAX      DisplayString
    MAX-ACCESS  read-only
    STATUS      current
    DESCRIPTION
            "A textual string describing the failover policy."

        ::=     { failoverPolicyEntry 4 }


failoverPolicySelectionPolicy OBJECT-TYPE
    SYNTAX      FOPSelectionPolicyType
    MAX-ACCESS  read-only
    STATUS      current
    DESCRIPTION
            "Indicates the selection policy used by the failover policy
            to determine the next pServer to host the application or
            load balancer."

        ::=     { failoverPolicyEntry 5 }


failoverPolicyAutoFailback OBJECT-TYPE
    SYNTAX      TruthValue
    MAX-ACCESS  read-only
    STATUS      current
    DESCRIPTION
            "Indicates whether or not the failover policy is configured for
            auto-failback"

        ::=     { failoverPolicyEntry 6 }


failoverPolicyRebootPServer OBJECT-TYPE
    SYNTAX      TruthValue
    MAX-ACCESS  read-only
    STATUS      current
    DESCRIPTION
            "Indicates wether or not the pServer failed over from should
            be rebooted"

        ::=     { failoverPolicyEntry 7 }

-- failover policy member pServers
failoverPolicyPServerTable   OBJECT-TYPE
    SYNTAX      SEQUENCE OF FailoverPolicyPServerEntry
    MAX-ACCESS  not-accessible
    STATUS      current
    DESCRIPTION
            "A list of entries describing failover policy member pServers."

        ::=     { failoverPolicies 2 }


failoverPolicyPServerEntry OBJECT-TYPE
    SYNTAX      FailoverPolicyPServerEntry
    MAX-ACCESS  not-accessible
    STATUS      current
    DESCRIPTION
            "A list of attributes describing each failover policy pServer
            member"

    INDEX       { lPanIndex, failoverPolicyIndex, failoverPolicyPServerIndex }
        ::=     { failoverPolicyPServerTable 1 }


FailoverPolicyPServerEntry ::=
    SEQUENCE {
        failoverPolicyPServerIndex
            Integer32,
        failoverPolicyPServerOrder
            Integer32
    }


failoverPolicyPServerIndex OBJECT-TYPE
    SYNTAX      Integer32 (1..2147483647)
    MAX-ACCESS  read-only
    STATUS      current
    DESCRIPTION
            "An integer value identifying the pServerIndex value of the
            pServer member of this failover policy."

        ::=     { failoverPolicyPServerEntry 1 }

failoverPolicyPServerOrder OBJECT-TYPE
    SYNTAX      Integer32
    MAX-ACCESS  read-only
    STATUS      current
    DESCRIPTION
            "An integer value identifying the activation order of this pServer
            within the failover policy."

        ::=     { failoverPolicyPServerEntry 2 }


healthMonitors OBJECT IDENTIFIER ::= { applicationResources 2 }


HealthMonPolicyType ::= TEXTUAL-CONVENTION
    STATUS      current
    DESCRIPTION
            "Describes health monitor action policies."
    SYNTAX INTEGER {
        any-started(1),
        all-started(2),
        undefined(999)
    }


healthMonitorTable   OBJECT-TYPE
    SYNTAX      SEQUENCE OF HealthMonitorEntry
    MAX-ACCESS  not-accessible
    STATUS      current
    DESCRIPTION
            "A list of entries describing application/load balancer
            health monitors."

        ::=     { healthMonitors 1 }


healthMonitorEntry OBJECT-TYPE
    SYNTAX      HealthMonitorEntry
    MAX-ACCESS  not-accessible
    STATUS      current
    DESCRIPTION
            "A list of attributes describing a failover policy"

    INDEX       { lPanIndex, healthMonitorIndex }
        ::=     { healthMonitorTable 1 }


HealthMonitorEntry ::=
    SEQUENCE {
        healthMonitorIndex
            Integer32,
        healthMonitorLPANIndex
            Integer32,
        healthMonitorName
            DisplayString,
        healthMonitorDescription
            DisplayString,
        healthMonitorScript
            DisplayString,
        healthMonitorRestartPolicy
            HealthMonPolicyType,
        healthMonitorRestartThreshold
            Integer32,
        healthMonitorFailoverPolicy
            HealthMonPolicyType,
        healthMonitorFailoverThreshold
            Integer32,
        healthMonitorGiveupPolicy
            HealthMonPolicyType,
        healthMonitorGiveupThreshold
            Integer32
    }

healthMonitorIndex OBJECT-TYPE
    SYNTAX      Integer32 (1..2147483647)
    MAX-ACCESS  read-only
    STATUS      current
    DESCRIPTION
            "An integer value identifying the health monitor within the
            LPAN."

        ::=     { healthMonitorEntry 1 }


healthMonitorLPANIndex OBJECT-TYPE
    SYNTAX      Integer32 (1..2147483647)
    MAX-ACCESS  read-only
    STATUS      current
    DESCRIPTION
            "An integer value identifying the lPanIndex value of the
            LPAN that hosts this health monitor."

        ::=     { healthMonitorEntry 2 }


healthMonitorName OBJECT-TYPE
    SYNTAX      DisplayString
    MAX-ACCESS  read-only
    STATUS      current
    DESCRIPTION
            "A textual string identifying the health monitor."

        ::=     { healthMonitorEntry 3 }


healthMonitorDescription OBJECT-TYPE
    SYNTAX      DisplayString
    MAX-ACCESS  read-only
    STATUS      current
    DESCRIPTION
            "A textual string describing the health monitor."

        ::=     { healthMonitorEntry 4 }


healthMonitorScript OBJECT-TYPE
    SYNTAX      DisplayString
    MAX-ACCESS  read-only
    STATUS      current
    DESCRIPTION
            "The health monitor script (and arguments) used to test the
            health of the application."

        ::=     { healthMonitorEntry 5 }


healthMonitorRestartPolicy OBJECT-TYPE
    SYNTAX      HealthMonPolicyType
    MAX-ACCESS  read-only
    STATUS      current
    DESCRIPTION
            "Indicates whether any health monitor or all health monitors
            must reach the configured threshold before a restart is invoked."

        ::=     { healthMonitorEntry 6 }


healthMonitorRestartThreshold OBJECT-TYPE
    SYNTAX      Integer32
    MAX-ACCESS  read-only
    STATUS      current
    DESCRIPTION
            "The number of consecutive health monitor detected failures
            required before a restart is invoked on the monitored application
            or load balancer"

        ::=     { healthMonitorEntry 7 }


healthMonitorFailoverPolicy OBJECT-TYPE
    SYNTAX      HealthMonPolicyType
    MAX-ACCESS  read-only
    STATUS      current
    DESCRIPTION
            "Indicates whether any health monitor or all health monitors
            must reach the configured threshold before a failover is invoked."

        ::=     { healthMonitorEntry 8 }


healthMonitorFailoverThreshold OBJECT-TYPE
    SYNTAX      Integer32
    MAX-ACCESS  read-only
    STATUS      current
    DESCRIPTION
            "The number of consecutive health monitor detected failures
            required before a failover is invoked on the monitored application
            or load balancer"

        ::=     { healthMonitorEntry 9 }


healthMonitorGiveupPolicy OBJECT-TYPE
    SYNTAX      HealthMonPolicyType
    MAX-ACCESS  read-only
    STATUS      current
    DESCRIPTION
            "Indicates whether any health monitor or all health monitors
            must reach the configured threshold before a give-up occurs."

        ::=     { healthMonitorEntry 10 }


healthMonitorGiveupThreshold OBJECT-TYPE
    SYNTAX      Integer32 (1..2147483647)
    MAX-ACCESS  read-only
    STATUS      current
    DESCRIPTION
            "The number of consecutive health monitor detected failures
            required before a givup occurs for the monitored application
            or load balancer"

        ::=     { healthMonitorEntry 11 }


healthMonitorPServerTable   OBJECT-TYPE
    SYNTAX      SEQUENCE OF HealthMonitorPServerEntry
    MAX-ACCESS  not-accessible
    STATUS      current
    DESCRIPTION
            "A list of entries describing pServers that host this
            health monitor."

        ::=     { healthMonitors 2 }


healthMonitorPServerEntry OBJECT-TYPE
    SYNTAX      HealthMonitorPServerEntry
    MAX-ACCESS  not-accessible
    STATUS      current
    DESCRIPTION
            "A list of attributes describing a health monitor host pServer."

    INDEX       { lPanIndex, healthMonitorIndex, healthMonitorPServerIndex }
        ::=     { healthMonitorPServerTable 1 }


HealthMonitorPServerEntry ::=
    SEQUENCE {
        healthMonitorPServerIndex
            Integer32,
        healthMonitorInterval
            Integer32,
        healthMonitorStartupDelay
            Integer32
    }

healthMonitorPServerIndex OBJECT-TYPE
    SYNTAX      Integer32 (1..2147483647)
    MAX-ACCESS  read-only
    STATUS      current
    DESCRIPTION
            "An integer value identifying the pServerIndex value of the
            pServer that hosts this health monitor.  The value 999 is used
            to identify the 'local' pServer.  If local settings are configured,
            the health monitor will use these settings whenever the monitor
            and the monitored application or load balancer are hosted by the
            same pServer."

        ::=     { healthMonitorPServerEntry 1 }


healthMonitorInterval OBJECT-TYPE
    SYNTAX      Integer32
    MAX-ACCESS  read-only
    STATUS      current
    DESCRIPTION
            "The polling frequency in seconds that this monitor test an
            application or loadbalancer health."

        ::=     { healthMonitorPServerEntry 2 }


healthMonitorStartupDelay OBJECT-TYPE
    SYNTAX      Integer32
    MAX-ACCESS  read-only
    STATUS      current
    DESCRIPTION
            "The startup dely in seconds that this monitor waits after
            application or loadbalancer start before the monitor begins
            checking the health of the application or load balancer."

        ::=     { healthMonitorPServerEntry 3 }


executableResources OBJECT IDENTIFIER ::= { applicationResources 3 }


executableResourceTable   OBJECT-TYPE
    SYNTAX      SEQUENCE OF ExecutableResourceEntry
    MAX-ACCESS  not-accessible
    STATUS      current
    DESCRIPTION
            "A list of entries describing application/load balancer
            executable resources."

        ::=     { executableResources 1 }


executableResourceEntry OBJECT-TYPE
    SYNTAX      ExecutableResourceEntry
    MAX-ACCESS  not-accessible
    STATUS      current
    DESCRIPTION
            "A list of attributes describing an executable resource."

    INDEX       { lPanIndex, executableResourceIndex }
        ::=     { executableResourceTable 1 }


ExecutableResourceEntry ::=
    SEQUENCE {
        executableResourceIndex
            Integer32,
        executableResourceLPANIndex
            Integer32,
        executableResourceName
            DisplayString,
        executableResourceDescription
            DisplayString,
        executableResourceUser
            DisplayString,
        executableResourceCommand
            DisplayString,
        executableResourceStartArgs
            DisplayString,
        executableResourceStopArgs
            DisplayString,
        executableResourceExecuteArgs
            DisplayString
    }


executableResourceIndex OBJECT-TYPE
    SYNTAX      Integer32 (1..2147483647)
    MAX-ACCESS  read-only
    STATUS      current
    DESCRIPTION
            "An integer value identifying the executable resource within the
            LPAN."

        ::=     { executableResourceEntry 1 }


executableResourceLPANIndex OBJECT-TYPE
    SYNTAX      Integer32 (1..2147483647)
    MAX-ACCESS  read-only
    STATUS      current
    DESCRIPTION
            "An integer value identifying the lPanIndex value of the
            LPAN that hosts this executable resource."

        ::=     { executableResourceEntry 2 }


executableResourceName OBJECT-TYPE
    SYNTAX      DisplayString
    MAX-ACCESS  read-only
    STATUS      current
    DESCRIPTION
            "A textual string identifying the executable resource."

        ::=     { executableResourceEntry 3 }


executableResourceDescription OBJECT-TYPE
    SYNTAX      DisplayString
    MAX-ACCESS  read-only
    STATUS      current
    DESCRIPTION
            "A textual string describing the executable resource."

        ::=     { executableResourceEntry 4 }


executableResourceUser OBJECT-TYPE
    SYNTAX      DisplayString
    MAX-ACCESS  read-only
    STATUS      current
    DESCRIPTION
            "A textual string identifying the user that will execute
            the resource."

        ::=     { executableResourceEntry 5 }


executableResourceCommand OBJECT-TYPE
    SYNTAX      DisplayString
    MAX-ACCESS  read-only
    STATUS      current
    DESCRIPTION
            "A textual string identifying the command used to start, stop,
            or execute the application or resource."

        ::=     { executableResourceEntry 6 }


executableResourceStartArgs OBJECT-TYPE
    SYNTAX      DisplayString
    MAX-ACCESS  read-only
    STATUS      current
    DESCRIPTION
            "A textual string identifying the arguments passed to the
            command when starting an application or resoruce."

        ::=     { executableResourceEntry 7 }


executableResourceStopArgs OBJECT-TYPE
    SYNTAX      DisplayString
    MAX-ACCESS  read-only
    STATUS      current
    DESCRIPTION
            "A textual string identifying the arguments passed to the
            command when stopping an application or resource."

        ::=     { executableResourceEntry 8 }

executableResourceExecuteArgs OBJECT-TYPE
    SYNTAX      DisplayString
    MAX-ACCESS  read-only
    STATUS      current
    DESCRIPTION
            "A textual string identifying the arguments passed to the
            command when executing an application or resource."

        ::=     { executableResourceEntry 9 }


scsiDiskResources OBJECT IDENTIFIER ::= { applicationResources 4 }


scsiDiskResourceTable   OBJECT-TYPE
    SYNTAX      SEQUENCE OF ScsiDiskResourceEntry
    MAX-ACCESS  not-accessible
    STATUS      current
    DESCRIPTION
            "A list of entries describing SCSI disk resources."

        ::=     { scsiDiskResources 1 }


scsiDiskResourceEntry OBJECT-TYPE
    SYNTAX      ScsiDiskResourceEntry
    MAX-ACCESS  not-accessible
    STATUS      current
    DESCRIPTION
            "A list of attributes describing each SCSI disk resource."

    INDEX       { lPanIndex, scsiDiskResourceIndex }
        ::=     { scsiDiskResourceTable 1 }


ScsiDiskResourceEntry ::=
    SEQUENCE {
        scsiDiskResourceIndex
            Integer32,
        scsiDiskResourceLPANIndex
            Integer32,
        scsiDiskResourceName
            DisplayString,
        scsiDiskResourceDescription
            DisplayString,
        scsiDiskResourceDiskId
            DisplayString,
        scsiDiskResourceDiskIdOctets
            OCTET STRING
    }


scsiDiskResourceIndex OBJECT-TYPE
    SYNTAX      Integer32 (1..2147483647)
    MAX-ACCESS  read-only
    STATUS      current
    DESCRIPTION
            "An integer value identifying the SCSI disk resource within the
            LPAN."

        ::=     { scsiDiskResourceEntry 1 }


scsiDiskResourceLPANIndex OBJECT-TYPE
    SYNTAX      Integer32 (1..2147483647)
    MAX-ACCESS  read-only
    STATUS      current
    DESCRIPTION
            "An integer value identifying the lPanIndex value of the
            LPAN that hosts this SCSI disk resource."

        ::=     { scsiDiskResourceEntry 2 }


scsiDiskResourceName OBJECT-TYPE
    SYNTAX      DisplayString
    MAX-ACCESS  read-only
    STATUS      current
    DESCRIPTION
            "A textual string identifying the SCSI disk resource."

        ::=     { scsiDiskResourceEntry 3 }


scsiDiskResourceDescription OBJECT-TYPE
    SYNTAX      DisplayString
    MAX-ACCESS  read-only
    STATUS      current
    DESCRIPTION
            "A textual string describing the SCSI disk resource."

        ::=     { scsiDiskResourceEntry 4 }


scsiDiskResourceDiskId OBJECT-TYPE
    SYNTAX      DisplayString
    MAX-ACCESS  read-only
    STATUS      current
    DESCRIPTION
            "A human readable string consisting of dot separated values
            of HBA number, BUS ID, target device ID and LUN of the SCSI
            disk contained in this resource"

        ::=     { scsiDiskResourceEntry 5 }


scsiDiskResourceDiskIdOctets OBJECT-TYPE
    SYNTAX      OCTET STRING (SIZE(4))
    MAX-ACCESS  read-only
    STATUS      current
    DESCRIPTION
            "A sequence of 4 bytes encoding the values of HBA number,
            BUS ID, target device ID and LUN of the SCSI disk contained
            in this resource"

        ::=     { scsiDiskResourceEntry 6 }



AccessMode ::= TEXTUAL-CONVENTION
    STATUS      current
    DESCRIPTION
            "Describes mount point access policies."
    SYNTAX INTEGER {
        access-read-only(1),
        access-read-write(2),
        undefined(999)
    }

scsiDiskResMountPtTable   OBJECT-TYPE
    SYNTAX      SEQUENCE OF ScsiDiskResMountPtEntry
    MAX-ACCESS  not-accessible
    STATUS      current
    DESCRIPTION
            "A list of entries describing SCSI disk resources mount
            points."

        ::=     { scsiDiskResources 2 }


scsiDiskResMountPtEntry OBJECT-TYPE
    SYNTAX      ScsiDiskResMountPtEntry
    MAX-ACCESS  not-accessible
    STATUS      current
    DESCRIPTION
            "A list of attributes describing each SCSI disk resource
            mount point"

    INDEX       { lPanIndex, scsiDiskResourceIndex, scsiDiskResMountPtIndex }
        ::=     { scsiDiskResMountPtTable 1 }


ScsiDiskResMountPtEntry ::=
    SEQUENCE {
        scsiDiskResMountPtIndex
            Integer32,
        scsiDiskResMountPtName
            DisplayString,
        scsiDiskResMountPtPartition
            DisplayString,
        scsiDiskResMountPtAccessMode
            AccessMode,
        scsiDiskResMountPtCreateMount
            TruthValue,
        scsiDiskResMountPtScanDisk
            TruthValue,
        scsiDiskResMountPtOrder
            Integer32,
        scsiDiskResMountPtMountOption
            DisplayString
    }


scsiDiskResMountPtIndex OBJECT-TYPE
    SYNTAX      Integer32 (1..2147483647)
    MAX-ACCESS  read-only
    STATUS      current
    DESCRIPTION
            "An integer value identifying the SCSI disk resource mount point
            within the SCSI disk resource."

        ::=     { scsiDiskResMountPtEntry 1 }


scsiDiskResMountPtName OBJECT-TYPE
    SYNTAX      DisplayString
    MAX-ACCESS  read-only
    STATUS      current
    DESCRIPTION
            "The path name of the mount point"

        ::=     { scsiDiskResMountPtEntry 2 }


scsiDiskResMountPtPartition OBJECT-TYPE
    SYNTAX      DisplayString
    MAX-ACCESS  read-only
    STATUS      current
    DESCRIPTION
            "An integer value identifying the partition number on the SCSI
            disk containing the file system to be mounted."

        ::=     { scsiDiskResMountPtEntry 3 }


scsiDiskResMountPtAccessMode OBJECT-TYPE
    SYNTAX      AccessMode
    MAX-ACCESS  read-only
    STATUS      current
    DESCRIPTION
            "Indicates whether the file system is mounted read-only or
            read-write."

        ::=     { scsiDiskResMountPtEntry 4 }


scsiDiskResMountPtCreateMount OBJECT-TYPE
    SYNTAX      TruthValue
    MAX-ACCESS  read-only
    STATUS      current
    DESCRIPTION
            "Indicates whether or not the mount point should be created
            if it does not exist."

        ::=     { scsiDiskResMountPtEntry 5 }


scsiDiskResMountPtScanDisk OBJECT-TYPE
    SYNTAX      TruthValue
    MAX-ACCESS  read-only
    STATUS      current
    DESCRIPTION
            "Indicates whether or not the disk should be scanned
            prior to mounting."

        ::=     { scsiDiskResMountPtEntry 6 }


scsiDiskResMountPtOrder OBJECT-TYPE
    SYNTAX      Integer32
    MAX-ACCESS  read-only
    STATUS      current
    DESCRIPTION
            "Indicates the order in which the file system should be mounted.
            0 indicates unordered mounting."

        ::=     { scsiDiskResMountPtEntry 7 }


scsiDiskResMountPtMountOption OBJECT-TYPE
    SYNTAX      DisplayString
    MAX-ACCESS  read-only
    STATUS      current
    DESCRIPTION
            "Indicates any options to be used when mounting the filesystem."

        ::=     { scsiDiskResMountPtEntry 8 }


nfsResources OBJECT IDENTIFIER ::= { applicationResources 5 }


nfsResourceTable   OBJECT-TYPE
    SYNTAX      SEQUENCE OF NfsResourceEntry
    MAX-ACCESS  not-accessible
    STATUS      current
    DESCRIPTION
            "A list of entries describing NFS resources."

        ::=     { nfsResources 1 }


nfsResourceEntry OBJECT-TYPE
    SYNTAX      NfsResourceEntry
    MAX-ACCESS  not-accessible
    STATUS      current
    DESCRIPTION
            "A list of attributes describing each NFS resource."

    INDEX       { lPanIndex, nfsResourceIndex }
        ::=     { nfsResourceTable 1 }


NfsResourceEntry ::=
    SEQUENCE {
        nfsResourceIndex
            Integer32,
        nfsResourceLPANIndex
            Integer32,
        nfsResourceName
            DisplayString,
        nfsResourceDescription
            DisplayString,
        nfsResourceHostName
            DisplayString,
        nfsResourceHostFileSystem
            DisplayString,
        nfsResourceAccessMode
            AccessMode,
        nfsResourceUser
            DisplayString,
        nfsResourceMountPoint
            DisplayString,
        nfsResourceCreateMountPt
            TruthValue,
        nfsResourceMountOption
            DisplayString
    }


nfsResourceIndex OBJECT-TYPE
    SYNTAX      Integer32 (1..2147483647)
    MAX-ACCESS  read-only
    STATUS      current
    DESCRIPTION
            "An integer value identifying the NFS resource resource within the
            LPAN."

        ::=     { nfsResourceEntry 1 }


nfsResourceLPANIndex OBJECT-TYPE
    SYNTAX      Integer32 (1..2147483647)
    MAX-ACCESS  read-only
    STATUS      current
    DESCRIPTION
            "An integer value identifying the lPanIndex value of the
            LPAN that hosts this NFS resource."

        ::=     { nfsResourceEntry 2 }


nfsResourceName OBJECT-TYPE
    SYNTAX      DisplayString
    MAX-ACCESS  read-only
    STATUS      current
    DESCRIPTION
            "A textual string identifying the NFS resource."

        ::=     { nfsResourceEntry 3 }


nfsResourceDescription OBJECT-TYPE
    SYNTAX      DisplayString
    MAX-ACCESS  read-only
    STATUS      current
    DESCRIPTION
            "A textual string describing the NFS resource."

        ::=     { nfsResourceEntry 4 }


nfsResourceHostName OBJECT-TYPE
    SYNTAX      DisplayString
    MAX-ACCESS  read-only
    STATUS      current
    DESCRIPTION
            "A textual string identifying the host name (or IP address) that
            hosts this resource."

        ::=     { nfsResourceEntry 5 }


nfsResourceHostFileSystem OBJECT-TYPE
    SYNTAX      DisplayString
    MAX-ACCESS  read-only
    STATUS      current
    DESCRIPTION
            "The path name of the exported NFS filesystem."

        ::=     { nfsResourceEntry 7 }


nfsResourceAccessMode OBJECT-TYPE
    SYNTAX      AccessMode
    MAX-ACCESS  read-only
    STATUS      current
    DESCRIPTION
            "Indicates whether the NFS filesystem is mounted read-only or
            read-write."

        ::=     { nfsResourceEntry 8 }


nfsResourceUser OBJECT-TYPE
    SYNTAX      DisplayString
    MAX-ACCESS  read-only
    STATUS      current
    DESCRIPTION
            "A textual string identifying the user that will mount
            the NFS resource."

        ::=     { nfsResourceEntry 9 }


nfsResourceMountPoint OBJECT-TYPE
    SYNTAX      DisplayString
    MAX-ACCESS  read-only
    STATUS      current
    DESCRIPTION
            "The path of the mount point for the NFS resource."

        ::=     { nfsResourceEntry 10 }


nfsResourceCreateMountPt OBJECT-TYPE
    SYNTAX      TruthValue
    MAX-ACCESS  read-only
    STATUS      current
    DESCRIPTION
            "Indicates whether or not the mount point should be created
            if it doesn't already exist."

        ::=     { nfsResourceEntry 11 }


nfsResourceMountOption OBJECT-TYPE
    SYNTAX      DisplayString
    MAX-ACCESS  read-only
    STATUS      current
    DESCRIPTION
            "Indicates any options to be used when mounting the NFS resource."

        ::=     { nfsResourceEntry 12 }


networkResources OBJECT IDENTIFIER ::= { applicationResources 6 }

NetworkResourceType ::= TEXTUAL-CONVENTION
    STATUS      current
    DESCRIPTION
            "Describes network resource types."
    SYNTAX INTEGER {
         vEth(1),       -- network resource is associated with a specific vEth
         vSwitch(2),    -- network resource is associated with a specific vSwtich
         undefined(999)
    }


networkResourceTable   OBJECT-TYPE
    SYNTAX      SEQUENCE OF NetworkResourceEntry
    MAX-ACCESS  not-accessible
    STATUS      current
    DESCRIPTION
            "A list of entries describing NFS resources."

        ::=     { networkResources 1 }


networkResourceEntry OBJECT-TYPE
    SYNTAX      NetworkResourceEntry
    MAX-ACCESS  not-accessible
    STATUS      current
    DESCRIPTION
            "A list of attributes describing each NFS resource."

    INDEX       { lPanIndex, networkResourceIndex }
        ::=     { networkResourceTable 1 }


NetworkResourceEntry ::=
    SEQUENCE {
        networkResourceIndex
            Integer32,
        networkResourceLPANIndex
            Integer32,
        networkResourceName
            DisplayString,
        networkResourceDescription
            DisplayString,
        networkResourceType
            NetworkResourceType,
        networkResourceMACAddressOctets
            PhysAddress,
        networkResourceMACAddressString
            DisplayString,
        networkResourceRateLimit
            Integer32
    }


networkResourceIndex OBJECT-TYPE
    SYNTAX      Integer32 (1..2147483647)
    MAX-ACCESS  read-only
    STATUS      current
    DESCRIPTION
            "An integer value identifying the network resource within
            the LPAN."

        ::=     { networkResourceEntry 1 }


networkResourceLPANIndex OBJECT-TYPE
    SYNTAX      Integer32 (1..2147483647)
    MAX-ACCESS  read-only
    STATUS      current
    DESCRIPTION
            "An integer value identifying the lPanIndex value of the
            LPAN that hosts this network resource."

        ::=     { networkResourceEntry 2 }


networkResourceName OBJECT-TYPE
    SYNTAX      DisplayString
    MAX-ACCESS  read-only
    STATUS      current
    DESCRIPTION
            "A textual string identifying the network resource."

        ::=     { networkResourceEntry 3 }


networkResourceDescription OBJECT-TYPE
    SYNTAX      DisplayString
    MAX-ACCESS  read-only
    STATUS      current
    DESCRIPTION
            "A textual string describing the network resource."

        ::=     { networkResourceEntry 4 }


networkResourceType OBJECT-TYPE
    SYNTAX      NetworkResourceType
    MAX-ACCESS  read-only
    STATUS      current
    DESCRIPTION
            "Indicates whether the network resource is assigned to a specific
            vEth or to a specific vSwitch."

        ::=     { networkResourceEntry 5 }


networkResourceMACAddressOctets OBJECT-TYPE
    SYNTAX      PhysAddress
    MAX-ACCESS  read-only
    STATUS      current
    DESCRIPTION
            "An encoding of the network resource MAC address."

        ::=     { networkResourceEntry 6 }


networkResourceMACAddressString OBJECT-TYPE
    SYNTAX      DisplayString
    MAX-ACCESS  read-only
    STATUS      current
    DESCRIPTION
            "A human readable string representing the newtork resource
            MAC address in the form: '6E:4A:1F:00:01:06'."

        ::=     { networkResourceEntry 7 }


networkResourceRateLimit OBJECT-TYPE
    SYNTAX      Integer32
    MAX-ACCESS  read-only
    STATUS      current
    DESCRIPTION
            "The configured rate limit for the network resource in Mbps, 0
            indicates none or not applicable."

        ::=     { networkResourceEntry 8 }


networkResourceIPTable   OBJECT-TYPE
    SYNTAX      SEQUENCE OF NetworkResourceIPEntry
    MAX-ACCESS  not-accessible
    STATUS      current
    DESCRIPTION
            "A list of IP entries associated with each network resource."

        ::=     { networkResources 2 }


networkResourceIPEntry OBJECT-TYPE
    SYNTAX      NetworkResourceIPEntry
    MAX-ACCESS  not-accessible
    STATUS      current
    DESCRIPTION
            "A list of attributes describing IP addresses associated with each
            network resource."

    INDEX       { lPanIndex, networkResourceIndex, networkResourceIPIndex }
        ::=     { networkResourceIPTable 1 }


NetworkResourceIPEntry ::=
    SEQUENCE {
        networkResourceIPIndex
            Integer32,
        networkResourceIPAddress
            IpAddress,
        networkResourceIPBroadcast
            IpAddress,
        networkResourceIPMask
            IpAddress
    }


networkResourceIPIndex OBJECT-TYPE
    SYNTAX      Integer32 (1..2147483647)
    MAX-ACCESS  read-only
    STATUS      current
    DESCRIPTION
            "An integer value identifying the network resource IP address
            within the network resource."

        ::=     { networkResourceIPEntry 1 }


networkResourceIPAddress OBJECT-TYPE
    SYNTAX      IpAddress
    MAX-ACCESS  read-only
    STATUS      current
    DESCRIPTION
            "The IP address configured on this network resource"

        ::=     { networkResourceIPEntry 2 }


networkResourceIPBroadcast OBJECT-TYPE
    SYNTAX      IpAddress
    MAX-ACCESS  read-only
    STATUS      current
    DESCRIPTION
            "The broadcast address configured on this network resource)"

        ::=     { networkResourceIPEntry 3 }


networkResourceIPMask OBJECT-TYPE
    SYNTAX      IpAddress
    MAX-ACCESS  read-only
    STATUS      current
    DESCRIPTION
            "The network mask configured on this network resource"

        ::=     { networkResourceIPEntry 4 }


-- egenera notifications

egeneraNotifications OBJECT IDENTIFIER ::= { management 1000 }

egeneraNotificationObjects OBJECT IDENTIFIER ::= { egeneraNotifications 1 }

-- The following objects can not be read from agents, they exist
-- only in traps sent by the agents.

egeneraTrapSeverity OBJECT-TYPE
    SYNTAX      Integer32
    MAX-ACCESS  read-only
    STATUS      current
    DESCRIPTION
            "An integer variable identifying trap severity.  This value is
            set and packaged in every notification or trap sent."

        ::=     { egeneraNotificationObjects 1 }


egeneraTrapMessage OBJECT-TYPE
    SYNTAX      DisplayString
    MAX-ACCESS  read-only
    STATUS      current
    DESCRIPTION
            "An string containing a message associated with each trap.  This
            value is set and packaged in every notification or trap sent."

        ::=     { egeneraNotificationObjects 2 }



snmpManagerAddress OBJECT-TYPE
    SYNTAX      DisplayString
    MAX-ACCESS  read-only
    STATUS      current
    DESCRIPTION
            "A string containing the source IP address of illegal SNMP
            requests."

        ::=     { egeneraNotificationObjects 3 }


sensorName OBJECT-TYPE
    SYNTAX      DisplayString
    MAX-ACCESS  read-only
    STATUS      current
    DESCRIPTION
            "The textual name of the hardware sensor contained in pBlade, cBlade
            and sBlade voltage, temperature, and fanspeed hardware sensor
            threshold events"

        ::=     { egeneraNotificationObjects 6 }

sensorThreshold OBJECT-TYPE
    SYNTAX      INTEGER
    MAX-ACCESS  read-only
    STATUS      current
    DESCRIPTION
            "The integer representation of the hardware threshold exceeded contained in
            hardware sensor threshold events.  Voltage values are multiplied by 100 and
            rounded to convert from float to integer, thus 2.98 => 298"

        ::=     { egeneraNotificationObjects 7 }


sensorValue OBJECT-TYPE
    SYNTAX      INTEGER
    MAX-ACCESS  read-only
    STATUS      current
    DESCRIPTION
            "The integer representation of the hardware sensor value contained in hardware
            sensor threshold events.  Voltage values are multiplied by 100 and rounted to
            convert from float to integer.  Thus 0.530 => 53"

        ::=     { egeneraNotificationObjects 8 }


monitorName OBJECT-TYPE
    SYNTAX      DisplayString
    MAX-ACCESS  read-only
    STATUS      current
    DESCRIPTION
            "The textual name of User Defined Monitor driving pServerUserMonitorTraps."

        ::=     { egeneraNotificationObjects 9 }


ruleName OBJECT-TYPE
    SYNTAX      DisplayString
    MAX-ACCESS  read-only
    STATUS      current
    DESCRIPTION
            "The textual name of User Defined Monitor Rule that was matched that drives
            pServerUserMonitorTraps."

        ::=     { egeneraNotificationObjects 10 }





bladeFrameNotifications OBJECT IDENTIFIER ::= { egeneraNotifications 4 }


bladeFrameUpEvent NOTIFICATION-TYPE
    OBJECTS {
                bladeFrameIndex,
                bladeFrameName,
                egeneraTrapSeverity,
                egeneraTrapMessage
            }
    STATUS      current
    DESCRIPTION
            "The notification generated when a BladeFrame enters the Egenera
            PAN (generally when powered on).

            This trap is driven by the 'frame.discover' event type.  This event
            type occurs early during PAN Manager startup, and indicates that the
            BladeFrame has been discovered and that the physical model is being
            constructed.  This trap is primarily intended for environments where
            multiple BladeFrames are managed in the same PAN, however multi-
            BladeFrame management is not yet supported.

            This event type is not user visible, and will not appear in
            CLI or GUI event queries.  The trap exists to satisfy early
            requirements documents.

            Severity: 5"

        ::=     { bladeFrameNotifications 1 }


bladeFrameDownEvent NOTIFICATION-TYPE
    OBJECTS {
                bladeFrameIndex,
                bladeFrameName,
                egeneraTrapSeverity,
                egeneraTrapMessage
            }
    STATUS      current
    DESCRIPTION
            "The notification generated when a BladeFrame departs the Egenera
            PAN (generally when powered off).

            This trap is currently not driven by any event, and thus is not
            emmitted.  The trap is intended to communicate when a BladeFrame
            departs from a BladeFarm in environments where multiple BladeFrames
            are managed in the same PAN, however multi-BladeFrame management
            is not yet supported.  The trap exists to satisfy early
            requirements documents."

        ::=     { bladeFrameNotifications 2 }


bladeFrameDeviceIdMismatchEvent NOTIFICATION-TYPE
    OBJECTS {
                bladeFrameIndex,
                bladeFrameName,
                egeneraTrapSeverity,
                egeneraTrapMessage
            }
    STATUS      current
    DESCRIPTION
            "The notification generated Master and Slave cBlades do not
            agree on SCSI device IDs.

            This trap is driven by the 'PAN Manager Device ID Mismatch'
            event type.

            Severity: 1"

        ::=     { bladeFrameNotifications 3 }


bladeFramePowerOverCommitEvent NOTIFICATION-TYPE
    OBJECTS {
                bladeFrameIndex,
                bladeFrameName,
                egeneraTrapSeverity,
                egeneraTrapMessage
            }
    STATUS      current
    DESCRIPTION
            "The notification generated when a power domain has been
            overcommited.

            This trap is driven by 'BladeFrame <framename> Power Domain
            <A|B|C|D> Over Attached Event' event types.

            Severity: 1"

        ::=     { bladeFrameNotifications 4 }


bladeFramePowerOverDrawEvent NOTIFICATION-TYPE
    OBJECTS {
                bladeFrameIndex,
                bladeFrameName,
                egeneraTrapSeverity,
                egeneraTrapMessage
            }
    STATUS      current
    DESCRIPTION
            "The notification generated when a power domain has been
            over drawn.

            This trap is driven by 'BladeFrame <framename> Power Domain
            <A|B|C|D> Over Powered Event' event types.

            Severity: 1"

        ::=     { bladeFrameNotifications 5 }


bladeFramePowerDeniedEvent NOTIFICATION-TYPE
    OBJECTS {
                bladeFrameIndex,
                bladeFrameName,
                egeneraTrapSeverity,
                egeneraTrapMessage
            }
    STATUS      current
    DESCRIPTION
            "The notification generated when a blade power-on is denied
            due to lack of power.

            This trap is driven by 'BladeFrame <framename> Power Domain
            <A|B|C|D> Power On Denied Event' event types.

            Severity: 1"

        ::=     { bladeFrameNotifications 6 }


bfArchiveCreateEvent NOTIFICATION-TYPE
    OBJECTS {
                bladeFrameIndex,
                bladeFrameName,
                egeneraTrapSeverity,
                egeneraTrapMessage
            }
    STATUS      current
    DESCRIPTION
            "The notification generated when an archive has been created.

            This trap is driven by the 'Archive creation' event type.

            Severity: 5"

        ::=     { bladeFrameNotifications 7 }


bfArchiveDeleteEvent NOTIFICATION-TYPE
    OBJECTS {
                bladeFrameIndex,
                bladeFrameName,
                egeneraTrapSeverity,
                egeneraTrapMessage
            }
    STATUS      current
    DESCRIPTION
            "The notification generated when an archive has been deleted.

            This trap is driven by the 'Archive deletion' event type.

            Severity: 5"

        ::=     { bladeFrameNotifications 8 }


bfArchiveSchedCreateEvent NOTIFICATION-TYPE
    OBJECTS {
                bladeFrameIndex,
                bladeFrameName,
                egeneraTrapSeverity,
                egeneraTrapMessage
            }
    STATUS      current
    DESCRIPTION
            "The notification generated when an archive schedule has been
            created.

            This trap is driven by the 'Archive schedule creation' event
            type.

            Severity: 5"

        ::=     { bladeFrameNotifications 9 }


bfArchiveSchedDeleteEvent NOTIFICATION-TYPE
    OBJECTS {
                bladeFrameIndex,
                bladeFrameName,
                egeneraTrapSeverity,
                egeneraTrapMessage
            }
    STATUS      current
    DESCRIPTION
            "The notification generated when an archive schedule has been
            deleted.

            This trap is driven by the 'Archive schedule deletion' event
            type.

            Severity: 5"

        ::=     { bladeFrameNotifications 10 }

bfArchiveSchedFailedEvent NOTIFICATION-TYPE
    OBJECTS {
                bladeFrameIndex,
                bladeFrameName,
                egeneraTrapSeverity,
                egeneraTrapMessage
            }
    STATUS      current
    DESCRIPTION
            "The notification generated when a scheduled archive fails in the
            PAN.

            This trap is driven by the 'Archive schedule failed' event type.

            Severity: 3"

        ::=     { bladeFrameNotifications 11 }


bfArchiveSchedModifiedEvent NOTIFICATION-TYPE
    OBJECTS {
                bladeFrameIndex,
                bladeFrameName,
                egeneraTrapSeverity,
                egeneraTrapMessage
            }
    STATUS      current
    DESCRIPTION
            "The notification generated when an archive schedule has been
            modified.

            This trap is driven by the 'Archive schedule modification' event
            type.

            Severity: 5"

        ::=     { bladeFrameNotifications 12 }


bfArchiveSchedRunningEvent NOTIFICATION-TYPE
    OBJECTS {
                bladeFrameIndex,
                bladeFrameName,
                egeneraTrapSeverity,
                egeneraTrapMessage
            }
    STATUS      current
    DESCRIPTION
            "The notification generated when an archive schedule is run.

            This trap is driven by the 'Archive schedule running' event
            type.

            Severity: 5"

        ::=     { bladeFrameNotifications 13 }


bladeFrameMasterRecoveredEvent NOTIFICATION-TYPE
    OBJECTS {
                bladeFrameIndex,
                bladeFrameName,
                egeneraTrapSeverity,
                egeneraTrapMessage
            }
    STATUS      current
    DESCRIPTION
            "The notification generated when a BladeFrame is available after
            a failover .

            This trap is driven by the 'BladeFrame Master Recovered Event'
            event type.

            This trap is deprecate as of 4.0.0.

            Severity: 5"

        ::=     { bladeFrameNotifications 14 }


bladeFrameREthMisconfigEvent NOTIFICATION-TYPE
    OBJECTS {
                bladeFrameIndex,
                bladeFrameName,
                egeneraTrapSeverity,
                egeneraTrapMessage
            }
    STATUS      current
    DESCRIPTION
            "The notification generated when a REth misconfiguration is
            detected.

            This trap is driven by the 'Reth Misconfiguration Event'
            event type.

            Severity: 3"

        ::=     { bladeFrameNotifications 15 }


bfPANManagerDowntimeEvent NOTIFICATION-TYPE
    OBJECTS {
                bladeFrameIndex,
                bladeFrameName,
                egeneraTrapSeverity,
                egeneraTrapMessage
            }
    STATUS      current
    DESCRIPTION
            "The notification generated when a PAN Manager reports its own
            downtime.

            This trap is driven by the 'PAN Manager <bladeframe>/c<1|2> Downtime
            Report Event' event type.

            Severity: 5"

        ::=     { bladeFrameNotifications 16 }


bfRccReportPeriodStartEvent NOTIFICATION-TYPE
    OBJECTS {
                bladeFrameIndex,
                bladeFrameName,
                egeneraTrapSeverity,
                egeneraTrapMessage
            }
    STATUS      current
    DESCRIPTION
            "The notification generated when the Resource Configuration
            Collector begins a reporting period.

            This trap is driven by the 'RCC Reporting Period Started Event'
            event type.

            Severity: 5"

        ::=     { bladeFrameNotifications 17 }


bfRccReportPeriodEndEvent NOTIFICATION-TYPE
    OBJECTS {
                bladeFrameIndex,
                bladeFrameName,
                egeneraTrapSeverity,
                egeneraTrapMessage
            }
    STATUS      current
    DESCRIPTION
            "The notification generated when the Resource Configuration
            Collector ends a reporting period.

            This trap is driven by the 'RCC Reporting Period Ended Event'
            event type.

            Severity: 5"

        ::=     { bladeFrameNotifications 18 }


bfRccExpiredFilesDeletedEvent NOTIFICATION-TYPE
    OBJECTS {
                bladeFrameIndex,
                bladeFrameName,
                egeneraTrapSeverity,
                egeneraTrapMessage
            }
    STATUS      current
    DESCRIPTION
            "The notification generated when the Resource Configuration
            Collector deletes expired files.

            This trap is driven by the 'RCC Expired Files Deleted'
            event type.

            Severity: 5"

        ::=     { bladeFrameNotifications 19 }

chassisOOBFailureEvent NOTIFICATION-TYPE
    OBJECTS {
                bladeFrameIndex,
                bladeFrameName,
                egeneraTrapSeverity,
                egeneraTrapMessage
            }
    STATUS      current
    DESCRIPTION
            "The notification generated when there is a failure to execute
            an Out of Band control operation on the chassis.

            This trap is driven by the 'Chassis OOB Failure' event type.

            Severity: 2"

        ::=     { bladeFrameNotifications 20 }

bladeDiscoveryCompletedEvent NOTIFICATION-TYPE
    OBJECTS {
                bladeFrameIndex,
                bladeFrameName,
                egeneraTrapSeverity,
                egeneraTrapMessage
            }
    STATUS      current
    DESCRIPTION
            "The notification generated when we finish the hardware discovery
            process of a blade successfully.  This trap will not be generated
            on all hardware platforms.

            This trap is driven by the 'Blade Discovery Completed'
            event type.

            Severity: 5"

        ::=     { bladeFrameNotifications 21 }

bladeDiscoveryFailedEvent NOTIFICATION-TYPE
    OBJECTS {
                bladeFrameIndex,
                bladeFrameName,
                egeneraTrapSeverity,
                egeneraTrapMessage
            }
    STATUS      current
    DESCRIPTION
            "The notification generated when we finish the hardware discovery
            process of a blade unsuccessfully.  This trap will not be generated
            on all hardware platforms.

            This trap is driven by the 'Blade Discovery Failed'
            event type.

            Severity: 2"

        ::=     { bladeFrameNotifications 22 }

bladeUndiscoveryCompletedEvent NOTIFICATION-TYPE
    OBJECTS {
                bladeFrameIndex,
                bladeFrameName,
                egeneraTrapSeverity,
                egeneraTrapMessage
            }
    STATUS      current
    DESCRIPTION
            "The notification generated when we finish the hardware undiscovery
            process of a blade successfully.  This trap will not be generated
            on all hardware platforms.

            This trap is driven by the 'Blade Undiscovery Completed'
            event type.

            Severity: 5"

        ::=     { bladeFrameNotifications 23 }

bladeUndiscoveryFailedEvent NOTIFICATION-TYPE
    OBJECTS {
                bladeFrameIndex,
                bladeFrameName,
                egeneraTrapSeverity,
                egeneraTrapMessage
            }
    STATUS      current
    DESCRIPTION
            "The notification generated when we finish the hardware undiscovery
            process of a blade unsuccessfully.  This trap will not be generated
            on all hardware platforms.

            This trap is driven by the 'Blade Undiscovery Failed'
            event type.

            Severity: 2"

        ::=     { bladeFrameNotifications 24 }

bfIArchiveExportStartEvent NOTIFICATION-TYPE
    OBJECTS {                  
                bladeFrameIndex,
                bladeFrameName,
                egeneraTrapSeverity,
                egeneraTrapmessage
            }         
    STATUS      current
    DESCRIPTION
            "The notification generated when a blade frame image archive export
            starts.
                                           
            This trap is driven by the 'Image Archive Export Start' event type.
                       
            Severity: 5"
                                           
        ::=     { bladeFrameNotifications 25 }

bfIArchiveExportFinishEvent NOTIFICATION-TYPE
    OBJECTS {                  
                bladeFrameIndex,
                bladeFrameName,    
                egeneraTrapSeverity,
                egeneraTrapmessage
            }         
    STATUS      current
    DESCRIPTION                            
            "The notification generated when a blade frame image archive export
            finishes.
                                           
            This trap is driven by the 'Image Archive Export Finish' event type.
                       
            Severity: 5"
                                           
        ::=     { bladeFrameNotifications 26 }

bfIArchiveExportFailureEvent NOTIFICATION-TYPE
    OBJECTS {                  
                bladeFrameIndex,
                bladeFrameName,
                egeneraTrapSeverity,
                egeneraTrapmessage
            }         
    STATUS      current
    DESCRIPTION
            "The notification generated when a blade frame image archive export
            fails.
                                           
            This trap is driven by the 'Image Archive Export Failure' event type.
                       
            Severity: 2"
                                           
        ::=     { bladeFrameNotifications 27 }

bfIArchiveRestoreStartEvent NOTIFICATION-TYPE
    OBJECTS {                  
                bladeFrameIndex,
                bladeFrameName,
                egeneraTrapSeverity,
                egeneraTrapmessage
            }         
    STATUS      current
    DESCRIPTION
            "The notification generated when a blade frame image archive
            restore starts.
                                           
            This trap is driven by the 'Image Archive Restore Start' event type.
                       
            Severity: 5"
                                           
        ::=     { bladeFrameNotifications 28 }

bfIArchiveRestoreFinishEvent NOTIFICATION-TYPE
    OBJECTS {                  
                bladeFrameIndex,
                bladeFrameName,    
                egeneraTrapSeverity,
                egeneraTrapmessage
            }         
    STATUS      current
    DESCRIPTION                            
            "The notification generated when a blade frame image archive
            restore finishes.
                                           
            This trap is driven by the 'Image Archive Restore Finish' event type.
                       
            Severity: 5"
                                           
        ::=     { bladeFrameNotifications 29 }

bfIArchiveRestoreFailureEvent NOTIFICATION-TYPE
    OBJECTS {
                bladeFrameIndex,
                bladeFrameName,
                egeneraTrapSeverity,
                egeneraTrapmessage
            }
    STATUS      current
    DESCRIPTION
            "The notification generated when a blade frame image archive
            restore fails.

            This trap is driven by the 'Image Archive Restore Failure' event type.

            Severity: 2"

        ::=     { bladeFrameNotifications 30 }

licenseAcquiredEvent NOTIFICATION-TYPE
    OBJECTS {
                bladeFrameIndex,
                bladeFrameName,
                egeneraTrapSeverity,
                egeneraTrapMessage
            }
    STATUS      current
    DESCRIPTION       
            "The notification generated when a license is used / acquired.
                      
            This trap is driven by the 'License Acquired' event type.
                      
            Severity: 5"
                      
        ::=     { bladeFrameNotifications 31 }

licenseReleasedEvent NOTIFICATION-TYPE
    OBJECTS {         
                bladeFrameIndex,
                bladeFrameName,
                egeneraTrapSeverity,
                egeneraTrapMessage
            }         
    STATUS      current
    DESCRIPTION       
            "The notification generated when a license is released.
                      
            This trap is driven by the 'License Released' event type.
                      
            Severity: 5"
                      
        ::=     { bladeFrameNotifications 32 }

licenseAcquireFailedEvent NOTIFICATION-TYPE
    OBJECTS {         
                bladeFrameIndex,
                bladeFrameName,
                egeneraTrapSeverity,
                egeneraTrapMessage
            }         
    STATUS      current
    DESCRIPTION       
            "The notification generated when an attempt to acquire a license
            fails.
                      
            This trap is driven by the 'License Acquire Failed' event type.
                      
            Severity: 3"
                      
        ::=     { bladeFrameNotifications 33 }

licenseAddedEvent NOTIFICATION-TYPE
    OBJECTS {         
                bladeFrameIndex,
                bladeFrameName,
                egeneraTrapSeverity,
                egeneraTrapMessage
            }         
    STATUS      current
    DESCRIPTION       
            "The notification generated when a license is added.
                      
            This trap is driven by the 'License Added' event type.
                      
            Severity: 5"
                      
        ::=     { bladeFrameNotifications 34 }

licenseUpdatedEvent NOTIFICATION-TYPE
    OBJECTS {         
                bladeFrameIndex,
                bladeFrameName,
                egeneraTrapSeverity,
                egeneraTrapMessage
            }         
    STATUS      current
    DESCRIPTION       
            "The notification generated when a license is updated.
                      
            This trap is driven by the 'License Updated' event type.
                      
            Severity: 5"
                      
        ::=     { bladeFrameNotifications 35 }

licenseRemovedEvent NOTIFICATION-TYPE
    OBJECTS {         
                bladeFrameIndex,
                bladeFrameName,
                egeneraTrapSeverity,
                egeneraTrapMessage
            }         
    STATUS      current
    DESCRIPTION
            "The notification generated when a license is removed.
                      
            This trap is driven by the 'License Removed' event type.

            Severity: 5"

        ::=     { bladeFrameNotifications 36 }


licenseInvalidEvent NOTIFICATION-TYPE
    OBJECTS {         
                bladeFrameIndex,
                bladeFrameName,
                egeneraTrapSeverity,
                egeneraTrapMessage
            }
    STATUS      current
    DESCRIPTION       
            "The notification generated when a license is found to be invalid.

            This trap is driven by the 'License Invalid' event type.

            Severity: 3"

        ::=     { bladeFrameNotifications 37 }

chassisOOBRecoveryEvent NOTIFICATION-TYPE
    OBJECTS {
                bladeFrameIndex,
                bladeFrameName,
                egeneraTrapSeverity,
                egeneraTrapMessage
            }
    STATUS      current
    DESCRIPTION
            "The notification generated when there is a recovery of 
            Out of Band operations on the chassis.

            This trap is driven by the 'Chassis OOB Recovery' event type.

            Severity: 5"

        ::=     { bladeFrameNotifications 38 }

rethStatusRedundantEvent NOTIFICATION-TYPE
    OBJECTS {
                bladeFrameIndex,
                bladeFrameName,
                rEthIndex,
                rEthName,
                egeneraTrapSeverity,
                egeneraTrapMessage
            }
    STATUS      current
    DESCRIPTION
            "The notification when a Redundant Ethernet transitions to
            the Redundant state (both Eths are known not to be Failed).

            This trap is driven by the 'reth <rethname> Redundant Event'
            event type.

            Severity: 5"

        ::=     { bladeFrameNotifications 50 }


rethStatusNotRedundantEvent NOTIFICATION-TYPE
    OBJECTS {
                bladeFrameIndex,
                bladeFrameName,
                rEthIndex,
                rEthName,
                egeneraTrapSeverity,
                egeneraTrapMessage
            }
    STATUS      current
    DESCRIPTION
            "The notification when a Redundant Ethernet transitions to
            the Not-Redundant state (One Eth is known not to be Failed,
            the other Eth is either Failed or Unknown).

            This trap is driven by the 'reth <rethname> Not-Redundant Event'
            event type.

            Severity: 2"

        ::=     { bladeFrameNotifications 51 }


rethStatusDegradedEvent NOTIFICATION-TYPE
    OBJECTS {
                bladeFrameIndex,
                bladeFrameName,
                rEthIndex,
                rEthName,
                egeneraTrapSeverity,
                egeneraTrapMessage
            }
    STATUS      current
    DESCRIPTION
            "The notification when a Redundant Ethernet transitions to
            the Degraded state (One Eth is known to be Failed, the other
            Eth is Unknown).

            This trap is driven by the 'reth <rethname> Degraded Event'
            event type.

            Severity: 1"

        ::=     { bladeFrameNotifications 52 }


rethStatusFailedEvent NOTIFICATION-TYPE
    OBJECTS {
                bladeFrameIndex,
                bladeFrameName,
                rEthIndex,
                rEthName,
                egeneraTrapSeverity,
                egeneraTrapMessage
            }
    STATUS      current
    DESCRIPTION
            "The notification when a Redundant Ethernet transitions to
            the Failed state (both Eths are known to be Failed).

            This trap is driven by the 'reth <rethname> Failed Event'
            event type.

            Severity: 1"

        ::=     { bladeFrameNotifications 53 }

bladeFramePanJoinEvent NOTIFICATION-TYPE
    OBJECTS {
                bladeFrameIndex,
                bladeFrameName,
                egeneraTrapSeverity,
                egeneraTrapMessage
            }
    STATUS      current
    DESCRIPTION
            "The notification generated when the bladeFrame joined PAN.

            This trap is driven by the 'PAN Join'
            event type.

            Severity: 5"

        ::=     { bladeFrameNotifications 20 }

cBladeNotifications OBJECT IDENTIFIER ::= { egeneraNotifications 5 }


cBladeInsertedEvent NOTIFICATION-TYPE
    OBJECTS {
                cBladeIndex,
                cBladeFrameIndex,
                cBladeName,
                egeneraTrapSeverity,
                egeneraTrapMessage
            }
    STATUS      current
    DESCRIPTION
            "The notification generated when a cBlade is inserted into
            a BladeFrame.

            This trap is driven by 'BladeFrame <framename> Blade Inserted Event'
            event types that describe cBlade insertions.

            Since the underlying event type describes pBlade, cBlade, and sBlade
            insertions, enabling/disabling this SNMP trap as an event action is
            bound to the enabling/disabling of pBladeInsertedEvent and
            sBladeInsertedEvent.

            Severity: 5"

        ::=     { cBladeNotifications 1 }


cBladeRemovedEvent NOTIFICATION-TYPE
    OBJECTS {
                cBladeIndex,
                cBladeFrameIndex,
                cBladeName,
                egeneraTrapSeverity,
                egeneraTrapMessage
            }
    STATUS      current
    DESCRIPTION
            "The notification generated when a cBlade is removed from
            a BladeFrame.

            This trap is driven by 'BladeFrame <framename> Blade Removed Event'
            event types that describe cBlade removal events.

            Since the underlying event type describes pBlade, cBlade, and sBlade
            removal, enabling/disabling this SNMP trap as an event action is
            bound to the enabling/disabling of pBladeRemovedEvent and
            sBladeRemovedEvent.

            Severity: 3"

        ::=     { cBladeNotifications 2 }


cBladePowerOnEvent NOTIFICATION-TYPE
    OBJECTS {
                cBladeIndex,
                cBladeFrameIndex,
                cBladeName,
                egeneraTrapSeverity,
                egeneraTrapMessage
            }
    STATUS      current
    DESCRIPTION
            "The notification generated when a cBlade is powered on.

            This trap is driven by 'Blade <framename>/c<1|2> Power Status Event'
            event types describing power on events.

            Since the underlying event type describes cBlade power on and off
            events, enabling/disabling this SNMP trap as an event action is bound
            to the enabling/disabling of cBladePowerOffEvent.  On BladeFrame ES
            Systems, this event type also comminicates power events for the
            cBlade daughter switch card, and thus enabling/disabling this trap
            is bound to enabling/disabling cBladeSwitchCardOnEvent and
            cBladeSwitchCardOffEvent.

            Severity: 5"

        ::=     { cBladeNotifications 3 }


cBladePowerOffEvent NOTIFICATION-TYPE
    OBJECTS {
                cBladeIndex,
                cBladeFrameIndex,
                cBladeName,
                egeneraTrapSeverity,
                egeneraTrapMessage
            }
    STATUS      current
    DESCRIPTION
            "The notification generated when a cBlade is powered off.

            This trap is driven by 'Blade <framename>/c<1|2> Power Status Event'
            event types describing power off events.

            Since the underlying event type describes cBlade power on and off
            events, enabling/disabling this SNMP trap as an event action is bound
            to the enabling/disabling of cBladePowerOnEvent.  On BladeFrame ES
            Systems, this event type also comminicates power events for the
            cBlade daughter switch card, and thus enabling/disabling this trap
            is bound to enabling/disabling cBladeSwitchCardOnEvent and
            cBladeSwitchCardOffEvent.

            Severity: 5"

        ::=     { cBladeNotifications 4 }


cBladeBootedEvent NOTIFICATION-TYPE
    OBJECTS {
                cBladeIndex,
                cBladeFrameIndex,
                cBladeName,
                egeneraTrapSeverity,
                egeneraTrapMessage
            }
    STATUS      current
    DESCRIPTION
            "The notification generated when a cBlade has successfully
            booted.

            This trap is driven by 'blade.status.monitor.event' event types
            that describe a cBlade transition from the booting state to the
            running state.

            This event type is not user visible, and will not appear in
            CLI or GUI event queries.  The trap exists to satisfy early
            requirements documents.

            Severity: 5"

        ::=     { cBladeNotifications 5 }


cBladeShutdownEvent NOTIFICATION-TYPE
    OBJECTS {
                cBladeIndex,
                cBladeFrameIndex,
                cBladeName,
                egeneraTrapSeverity,
                egeneraTrapMessage
            }
    STATUS      current
    DESCRIPTION
            "The notification generated when a cBlade has been shut
             down.

            This trap is driven by 'blade.status.monitor.event' event types
            that describe a cBlade transition from the shutting down state to
            the shutdown state.

            This event type is not user visible, and will not appear in
            CLI or GUI event queries.  The trap exists to satisfy early
            requirements documents.

            Severity: 5"

        ::=     { cBladeNotifications 6 }


cBladeEnabledEvent NOTIFICATION-TYPE
    OBJECTS {
                cBladeIndex,
                cBladeFrameIndex,
                cBladeName,
                egeneraTrapSeverity,
                egeneraTrapMessage
            }
    STATUS      current
    DESCRIPTION
            "The notification generated when a cBlade has been enabled
            (returns to service).

             This trap is driven by 'Blade <framename>/c<1|2> Out of Service Status
             false Event' event types.

             Severity: 5"

        ::=     { cBladeNotifications 7 }


cBladeDisabledEvent NOTIFICATION-TYPE
    OBJECTS {
                cBladeIndex,
                cBladeFrameIndex,
                cBladeName,
                egeneraTrapSeverity,
                egeneraTrapMessage
            }
    STATUS      current
    DESCRIPTION
            "The notification generated when a cBlade has been disabled
            (removed from service).

             This trap is driven by 'Blade <framename>/c<1|2> Out of Service Status
             true Event' event types.

             Severity: 5"

        ::=     { cBladeNotifications 8 }


cBladeSelectedEvent NOTIFICATION-TYPE
    OBJECTS {
                cBladeIndex,
                cBladeFrameIndex,
                cBladeName,
                egeneraTrapSeverity,
                egeneraTrapMessage
            }
    STATUS      current
    DESCRIPTION
            "The notification generated when a cBlade has been selected.

             This trap is driven by 'Blade <framename>/c<1|2> Selected Status
             true Event' even types.

             Severity: 5"

        ::=     { cBladeNotifications 9 }


cBladeDeselectedEvent NOTIFICATION-TYPE
    OBJECTS {
                cBladeIndex,
                cBladeFrameIndex,
                cBladeName,
                egeneraTrapSeverity,
                egeneraTrapMessage
            }
    STATUS      current
    DESCRIPTION
            "The notification generated when a cBlade has been unselected.

             This trap is driven by 'Blade <framename>/c<1|2> Selected Status
             false Event' even types.

             Severity: 5"

        ::=     { cBladeNotifications 10 }


cBladeMasterEvent NOTIFICATION-TYPE
    OBJECTS {
                cBladeIndex,
                cBladeFrameIndex,
                cBladeName,
                egeneraTrapSeverity,
                egeneraTrapMessage
            }
    STATUS      current
    DESCRIPTION
            "The notification generated when a cBlade has assumed the
            role of PAN Master.

            This trap is driven by 'PAN Manager <framename>/c<1|2> Start Event'
            event types that describe PAN Master initialization.

            Since the underlying event type describes PAN Manager started and
            master or slave initialization, enabling/disabling this SNMP trap
            as an event action is bound to the enabling/disabling of
            cBladeSlaveEvent and cBladePanManagerStartedEvent.

            Severity: 5"

        ::=     { cBladeNotifications 11 }


cBladeSlaveEvent NOTIFICATION-TYPE
    OBJECTS {
                cBladeIndex,
                cBladeFrameIndex,
                cBladeName,
                egeneraTrapSeverity,
                egeneraTrapMessage
            }
    STATUS      current
    DESCRIPTION
            "The notification generated when a cBlade has assumed the
            role of a PAN Slave.

            This trap is driven by 'PAN Manager <framename>/c<1|2> Start Event'
            event types that describe PAN Slave initialization.

            Since the underlying event type describes PAN Manager started and
            master or slave initialization, enabling/disabling this SNMP trap
            as an event action is bound to the enabling/disabling of
            cBladeMasterEvent and cBladePanManagerStartedEvent.

            Severity: 5"

        ::=     { cBladeNotifications 12 }


cBladeHwEvent NOTIFICATION-TYPE
    OBJECTS {
                cBladeIndex,
                cBladeFrameIndex,
                cBladeName,
                egeneraTrapSeverity,
                egeneraTrapMessage
            }
    STATUS      current
    DESCRIPTION
            "Encapsulates generic events from hardware.

            This trap is driven by 'Blade <framename>/c<1|2> non-sensor Event'
            event types that do not indicate panic, commanded shutdown,
            commanded reboot, or init level events.  Examples message contents
            include:

            OEM Type 0xe0, value = 0x64:0x21:0xce:0xe0:0x1d:0x00:0x00:0x00...
            bmc reset
            deasserted, value = 0x0211
            system booted

            Contact EES for more specific information.

            Since the underlying event type describes cBlade all non-sensor hardware
            events, and since there are specific traps for panic, commanded shutdown,
            commanded reboot, and init level events, enabling/disabling this SNMP trap
            as an event action is bound to the enabling/disabling of cBladePanicEvent,
            cBladeCmdShutdownEvent, cBladeCmdRebootEvent, cBladeCmdHaltEvent, and
            cBladeInitEvent.

            Severity: 3"

        ::=     { cBladeNotifications 13 }


--cBladeHwThreshEvent NOTIFICATION-TYPE
--    OBJECTS {
--                cBladeIndex,
--                cBladeFrameIndex,
--                cBladeName,
--                hwTheshComponent,
--                hwTheshLevel,
--                egeneraTrapSeverity,
--                egeneraTrapMessage
--            }
--    STATUS      current
--    DESCRIPTION
--            "Encapsulates hardward threshold events.
--
--            This trap has been deprecated in favor of cBladeVoltageUpperEvent,
--            cBladeVoltageLowerEvent, cBladeFanSpeedUpperEvent, cBladeFanSpeedLowerEvent,
--            cBladeTempUpperEvent, and cBladeTempLowerEvent."
--
--        ::=     { cBladeNotifications 14 }


cBladeSwitchCardOnEvent NOTIFICATION-TYPE
    OBJECTS {
                cBladeIndex,
                cBladeFrameIndex,
                cBladeName,
                egeneraTrapSeverity,
                egeneraTrapMessage
            }
    STATUS      current
    DESCRIPTION
            "Inicates the daughter switch card of cBladeES blades has
            been powered on.  This trap is only emitted from BladeFrame ES
            systems.

            This trap is driven by 'Blade <framename>/c<1|2> Power Status Event'
            event types describing cBladeES daughter switch card power on events.

            Since the underlying event type describes cBlade power on and off
            events, enabling/disabling this SNMP trap as an event action is bound
            to the enabling/disabling of cBladeSwitchCardOffEvent, cBladePowerOnEvent,
            and cBladePowerOffEvent.

            Severity: 5"

        ::=     { cBladeNotifications 15 }


cBladeSwitchCardOffEvent NOTIFICATION-TYPE
    OBJECTS {
                cBladeIndex,
                cBladeFrameIndex,
                cBladeName,
                egeneraTrapSeverity,
                egeneraTrapMessage
            }
    STATUS      current
    DESCRIPTION
            "Inicates the daughter switch card of cBladeES blades has
            been powered on.  This trap is only emitted from BladeFrame ES
            systems.

            This trap is driven by 'Blade <framename>/c<1|2> Power Status Event'
            event types describing cBladeES daughter switch card power off events.

            Since the underlying event type describes cBlade power on and off
            events, enabling/disabling this SNMP trap as an event action is bound
            to the enabling/disabling of cBladeSwitchCardOnEvent, cBladePowerOnEvent,
            and cBladePowerOffEvent.

            Severity: 5"

        ::=     { cBladeNotifications 16 }


cBladeFailureEvent NOTIFICATION-TYPE
    OBJECTS {
                cBladeIndex,
                cBladeFrameIndex,
                cBladeName,
                egeneraTrapSeverity,
                egeneraTrapMessage
            }
    STATUS      current
    DESCRIPTION
            "The notification generated when a cBlade fails.

            This trap is driven by 'PAN Manager cBlade Failure Event' event
            types.

            Severity: 1"

        ::=     { cBladeNotifications 17 }


cBladeMasterFailoverEvent NOTIFICATION-TYPE
    OBJECTS {
                cBladeIndex,
                cBladeFrameIndex,
                cBladeName,
                egeneraTrapSeverity,
                egeneraTrapMessage
            }
    STATUS      current
    DESCRIPTION
            "The notification generated when a cBlade has assumed the
            role of PAN Master after a failover.

            This trap is driven by 'PAN Manager <framename>/c<1|2> Failover Event'
            event types.

            Severity: 1"

        ::=     { cBladeNotifications 18 }


cBladeStonithEvent NOTIFICATION-TYPE
    OBJECTS {
                cBladeIndex,
                cBladeFrameIndex,
                cBladeName,
                egeneraTrapSeverity,
                egeneraTrapMessage
            }
    STATUS      current
    DESCRIPTION
            "The notification generated when one cBlade has stonithed
            the other.

            This trap is driven by 'PAN Manager cBlade Stonithed Event'
            event types.

            Severity: 1"

        ::=     { cBladeNotifications 19 }

-- The PAN Manager provides functionality to monitor messages from syslogd.
-- When properly configured and enabled, EES defines a set of strings to
-- search syslog messages for.  When encountered, these syslog messages are
-- promoted to Egenera PAN Manager events.  The search strings and event
-- severities are defined by EES.  There are 10 event types reserved for
-- cBlade syslog messages, and 10 event types reserved for pServer syslog
-- messages.  Contact EES for more information.

cBladeSyslogEvent NOTIFICATION-TYPE
    OBJECTS {
                cBladeIndex,
                cBladeFrameIndex,
                cBladeName,
                egeneraTrapSeverity,
                egeneraTrapMessage
            }
    STATUS      current
    DESCRIPTION
            "The notification sent when a syslog target string is emmited
            from the system logger.

            This trap is driven by 'Blade <framename>/c<1|2> Custom Linux
            System Message <1..10>' event types.  See 'eventtype -l' for
            more information.

            There are 10 cBlade syslog event types.  This trap can be
            enabled/disabled for each syslog event type independently.

            Severity: (configurable by EES, generally 1, 2 or 3)"

        ::=     { cBladeNotifications 20 }


cBladeSyslogDroppedEvent NOTIFICATION-TYPE
    OBJECTS {
                cBladeIndex,
                cBladeFrameIndex,
                cBladeName,
                egeneraTrapSeverity,
                egeneraTrapMessage
            }
    STATUS      current
    DESCRIPTION
            "The notification sent when a syslog target string message
            is dropped due to rate limiting.

            This trap is driven by 'Blade <framename>/c<1|2> Custom Linux System
            Messages dropped' event types.  System message events are subject
            to rate limiting.  By default, no more than 5 messages can be emitted
            during a 5 minute period.  If more than 5 target strings are
            encountered, events will only be created for the first 5 messages,
            subsequent messages will be dropped.  At the end of the 5 minute
            period, a 'Messages Dropped' event will be emmitted to indicate
            the number of dropped messages during the 5 minute period.
            Contact EES for more information.

            Severity: 3"

        ::=     { cBladeNotifications 21 }


cBladeSyslogPollingStoppedEvent NOTIFICATION-TYPE
    OBJECTS {
                cBladeIndex,
                cBladeFrameIndex,
                cBladeName,
                egeneraTrapSeverity,
                egeneraTrapMessage
            }
    STATUS      current
    DESCRIPTION
            "The notification sent when a syslog polling has stopped
            due to rate limiting.

            This trap is driven by the 'Blade MyBladeFrame/c1 Custom Linux
            System Messages polling stopped' event type.  System message events
            are subject to rate limiting.  By default, no more than 5 messages
            can be emitted during a 5 minute period.  If more than 5 target
            strings are encountered, events will only be created for the first
            5 messages, subsequent messages will be dropped.  If messages are
            dropped for 5 consecutive 5 minute periods, syslog message polling
            will be disabled on that cBlade.  Contact EES for more information.

            Severity: 2"

        ::=     { cBladeNotifications 22 }


-- The Egenera Precise Error Deamon (PED) is a component of cBlades that
-- corrolates egenera proprietary system messages.  A subset of these messages
-- are promoted to PAN Manager events, and exported via the following traps.
-- Contact EES for more information.

cBladePedDeadlockEvent NOTIFICATION-TYPE
    OBJECTS {
                cBladeIndex,
                cBladeFrameIndex,
                cBladeName,
                egeneraTrapSeverity,
                egeneraTrapMessage
            }
    STATUS      current
    DESCRIPTION
            "PED deadlock message.

            This trap is driven by 'Blade <framename>/c<1|2> PED Deadlock Avoidance
            Message' event types.  This trap encapsulates the following PED message
            types:
                EM24585
                EM24586

            Severity: 2"

        ::=     { cBladeNotifications 23 }


cBladePedFabricEvent NOTIFICATION-TYPE
    OBJECTS {
                cBladeIndex,
                cBladeFrameIndex,
                cBladeName,
                egeneraTrapSeverity,
                egeneraTrapMessage
            }
    STATUS      current
    DESCRIPTION
            "PED fabric message.

            This trap is driven by 'Blade <framename>/c<1|2> PED Fabric Message
            event types.  This trap encapsulates the following PED message
            types:
                EM16387
                EM16388
                EM16389
                EM16390
                EM16391
                EM16392
                EM24576
                EM24580
                EM24581
                EM24582
                EM24583
                EM24584
                EM24587
                EM24588
                EM24589
                EM24590
                EM24591
                EM24592

            Severity: 2"

        ::=     { cBladeNotifications 24 }

cBladePedLegacyEvent NOTIFICATION-TYPE
    OBJECTS {
                cBladeIndex,
                cBladeFrameIndex,
                cBladeName,
                egeneraTrapSeverity,
                egeneraTrapMessage
            }
    STATUS      current
    DESCRIPTION
            "PED legacy message

            This trap is driven by 'Blade <framename>/c<1|2> PED Legacy Message
            event types.  This trap encapsulates the following PED message
            types:
                EM24595

            Severity: 3"

        ::=     { cBladeNotifications 25 }


cBladePedOtherEvent NOTIFICATION-TYPE
    OBJECTS {
                cBladeIndex,
                cBladeFrameIndex,
                cBladeName,
                egeneraTrapSeverity,
                egeneraTrapMessage
            }
    STATUS      current
    DESCRIPTION
            "PED other message.

            This trap is driven by 'Blade <framename>/c<1|2> PED Message'
            event types.  This trap encapsulates any PED message not contained
            in any other specific PED event/trap types.

            Severity: 3"

        ::=     { cBladeNotifications 26 }


cBladePedNodeEvent NOTIFICATION-TYPE
    OBJECTS {
                cBladeIndex,
                cBladeFrameIndex,
                cBladeName,
                egeneraTrapSeverity,
                egeneraTrapMessage
            }
    STATUS      current
    DESCRIPTION
            "PED node message.

            This trap is driven by 'Blade <framename>/c<1|2> PED Node Message'
            event types.  This trap encapsulates the following PED message
            types:
                EM16385
                EM16386

            Severity: 3"

        ::=     { cBladeNotifications 27 }


cBladePedPathErrorEvent NOTIFICATION-TYPE
    OBJECTS {
                cBladeIndex,
                cBladeFrameIndex,
                cBladeName,
                egeneraTrapSeverity,
                egeneraTrapMessage
            }
    STATUS      current
    DESCRIPTION
            "PED path error message.

            This trap is driven by 'Blade <framename>/c<1|2> PED Path Error
            Message' event types.  This trap encapsulates the following PED
            message types:
                EM24593
                EM24594

            Severity: 2"

        ::=     { cBladeNotifications 28 }


cBladePedSerialBitEvent NOTIFICATION-TYPE
    OBJECTS {
                cBladeIndex,
                cBladeFrameIndex,
                cBladeName,
                egeneraTrapSeverity,
                egeneraTrapMessage
            }
    STATUS      current
    DESCRIPTION
            "PED serial bit message.

            This trap is driven by 'Blade <framename>/c<1|2> PED Serial Bit Message'
            event types.  This trap encapsulates the following PED message types:
                EM24577
                EM24578
                EM24579

            Severity: 2"

        ::=     { cBladeNotifications 29 }


cBladePedSwitchEvent NOTIFICATION-TYPE
    OBJECTS {
                cBladeIndex,
                cBladeFrameIndex,
                cBladeName,
                egeneraTrapSeverity,
                egeneraTrapMessage
            }
    STATUS      current
    DESCRIPTION
            "PED serial bit message.

            This trap is driven by 'Blade <framename>/c<1|2> PED Switch Message'
            event types.  This trap encapsulates the following PED message types:
                EM16384
                EM16393
                EM16394
                EM16395
                EM16396
                EM16397
                EM16398
                EM16399
                EM16400

            Severity: 2"

        ::=     { cBladeNotifications 30 }


cBladePedErrorEvent NOTIFICATION-TYPE
    OBJECTS {
                cBladeIndex,
                cBladeFrameIndex,
                cBladeName,
                egeneraTrapSeverity,
                egeneraTrapMessage
            }
    STATUS      current
    DESCRIPTION
            "PED error message.

            This trap is driven by 'Blade <framename>/c<1|2> PED Error Message'
            event types.  This trap encapsulates the following PED message types:
                EM24596
                EM24597
                EM24598

            Severity: 2"

        ::=     { cBladeNotifications 48 }



cBladePanicEvent NOTIFICATION-TYPE
    OBJECTS {
                cBladeIndex,
                cBladeFrameIndex,
                cBladeName,
                egeneraTrapSeverity,
                egeneraTrapMessage
            }
    STATUS      current
    DESCRIPTION
            "Encapsulates hardware events identifying cBlade panics that
            cause the cBlade to enter KDB, reboot, or halt'

            This trap is driven by 'Blade <framename>/c<1|2> non-sensor Event'
            event types that describe kernel panics.

            Contact EES for more specific information.

            Since the underlying event type describes cBlade non-sensor hardware
            events, and since there are specific traps for panic, commanded shutdown,
            commanded reboot, and init level events, enabling/disabling this SNMP trap
            as an event action is bound to the enabling/disabling of cBladeHwEvent,
            cBladeCmdShutdownEvent, cBladeCmdRebootEvent, cBladeCmdHaltEvent, and
            cBladeInitEvent.

            Severity: 3"

        ::=    { cBladeNotifications 31 }


cBladeCmdHaltEvent NOTIFICATION-TYPE
    OBJECTS {
                cBladeIndex,
                cBladeFrameIndex,
                cBladeName,
                egeneraTrapSeverity,
                egeneraTrapMessage
            }
    STATUS      current
    DESCRIPTION
            "Encapsulates hardware events indicating intentional cBlade
            halt.

            This trap is driven by 'Blade <framename>/c<1|2> non-sensor Event'
            event types that describe commanded halts.

            Contact EES for more specific information.

            Since the underlying event type describes cBlade non-sensor hardware
            events, and since there are specific traps for panic, commanded shutdown,
            commanded reboot, and init level events, enabling/disabling this SNMP trap
            as an event action is bound to the enabling/disabling of cBladeHwEvent,
            cBladeCmdShutdownEvent, cBladeCmdRebootEvent, cBladePanicEvent, and
            cBladeInitEvent.

            Severity: 3"

        ::=     { cBladeNotifications 32 }


cBladeCmdRebootEvent NOTIFICATION-TYPE
    OBJECTS {
                cBladeIndex,
                cBladeFrameIndex,
                cBladeName,
                egeneraTrapSeverity,
                egeneraTrapMessage
            }
    STATUS      current
    DESCRIPTION
            "Encapsulates hardware events indicating intentional cBlade
            reboot.

            This trap is driven by 'Blade <framename>/c<1|2> non-sensor Event'
            event types that describe commanded reboots.

            Contact EES for more specific information.

            Since the underlying event type describes cBlade non-sensor hardware
            events, and since there are specific traps for panic, commanded shutdown,
            commanded reboot, and init level events, enabling/disabling this SNMP trap
            as an event action is bound to the enabling/disabling of cBladeHwEventTrap,
            cBladeCmdShutdownEvent, cBladeCmdHaltEvent, cBladePanicEvent, and
            cBladeInitEvent.

            Severity: 3"

        ::=     { cBladeNotifications 33 }


cBladeInitEvent NOTIFICATION-TYPE
    OBJECTS {
                cBladeIndex,
                cBladeFrameIndex,
                cBladeName,
                egeneraTrapSeverity,
                egeneraTrapMessage
            }
    STATUS      current
    DESCRIPTION
            "Encapsulates hardware events indicating intentional cBlade
            has reached an init level.

            This trap is driven by 'Blade <framename>/c<1|2> non-sensor Event'
            event types that describe init level reached.

            Contact EES for more specific information.

            Since the underlying event type describes cBlade non-sensor hardware
            events, and since there are specific traps for panic, commanded shutdown,
            commanded reboot, and init level events, enabling/disabling this SNMP trap
            as an event action is bound to the enabling/disabling of cBladeHwEvent,
            cBladeCmdShutdownEvent, cBladeCmdHaltEvent, cBladeCmdRebootEvent, and
            cBladePanicEvent.

            Severity: 3"

        ::=     { cBladeNotifications 36 }


cBladeVoltageUpperEvent NOTIFICATION-TYPE
    OBJECTS {
                cBladeIndex,
                cBladeFrameIndex,
                cBladeName,
                sensorName,
                sensorThreshold,
                sensorValue,
                egeneraTrapSeverity,
                egeneraTrapMessage
            }
    STATUS      current
    DESCRIPTION
            "Encapsulates cBlade critical high voltage sensor events.

            This trap is driven by 'Blade <framename>/c<1|2> <voltage-sensor-name>
            Critical High Event' event types.

            The sensorValue and sensorThreshold fields are ingeter representations
            of real numbers.  The real numbers are multiplied by 100 and rounded
            to produce an integer, thus 0.530 => 53.

            This trap replaces cBladeHwThreshEvent.

            Severity: 3"

        ::=     { cBladeNotifications 37 }


cBladeVoltageLowerEvent NOTIFICATION-TYPE
    OBJECTS {
                cBladeIndex,
                cBladeFrameIndex,
                cBladeName,
                sensorName,
                sensorThreshold,
                sensorValue,
                egeneraTrapSeverity,
                egeneraTrapMessage
            }
    STATUS      current
    DESCRIPTION
            "Encapsulates cBlade critical low voltage sensor events.

            This trap is driven by 'Blade <framename>/c<1|2> <voltage-sensor-name>
            Critical Low Event' event types.

            The sensorValue and sensorThreshold fields are ingeter representations
            of real numbers.  The real numbers are multiplied by 100 and rounded
            to produce an integer, thus 0.530 => 53.

            This trap replaces cBladeHwThreshEvent.

            Severity: 3"

        ::=     { cBladeNotifications 38 }


cBladeFanSpeedUpperEvent NOTIFICATION-TYPE
    OBJECTS {
                cBladeIndex,
                cBladeFrameIndex,
                cBladeName,
                sensorName,
                sensorThreshold,
                sensorValue,
                egeneraTrapSeverity,
                egeneraTrapMessage
            }
    STATUS      current
    DESCRIPTION
            "Encapsulates cBlade critical high fan speed  sensor events.

            This trap is driven by 'Blade <framename>/c<1|2> <fan-sensor-name>
            Critical High Event' event types.

            This trap replaces cBladeHwThreshEvent.

            Severity: 3"

        ::=     { cBladeNotifications 39 }


cBladeFanSpeedLowerEvent NOTIFICATION-TYPE
    OBJECTS {
                cBladeIndex,
                cBladeFrameIndex,
                cBladeName,
                sensorName,
                sensorThreshold,
                sensorValue,
                egeneraTrapSeverity,
                egeneraTrapMessage
            }
    STATUS      current
    DESCRIPTION
            "Encapsulates cBlade critical low fan speed sensor events.

            This trap is driven by 'Blade <framename>/c<1|2> <fan-sensor-name>
            Critical Low Event' event types.

            This trap replaces cBladeHwThreshEvent.

            Severity: 3"

        ::=     { cBladeNotifications 40 }



cBladeTempUpperEvent NOTIFICATION-TYPE
    OBJECTS {
                cBladeIndex,
                cBladeFrameIndex,
                cBladeName,
                sensorName,
                sensorThreshold,
                sensorValue,
                egeneraTrapSeverity,
                egeneraTrapMessage
            }
    STATUS      current
    DESCRIPTION
            "Encapsulates cBlade critical high temperature sensor events.

            This trap is driven by 'Blade <framename>/c<1|2> <temp-sensor-name>
            Critical High Event' event types.

            This trap replaces cBladeHwThreshEvent.

            Severity: 3"

        ::=     { cBladeNotifications 41 }


cBladeTempLowerEvent NOTIFICATION-TYPE
    OBJECTS {
                cBladeIndex,
                cBladeFrameIndex,
                cBladeName,
                sensorName,
                sensorThreshold,
                sensorValue,
                egeneraTrapSeverity,
                egeneraTrapMessage
            }
    STATUS      current
    DESCRIPTION
            "Encapsulates cBlade critical low temperature sensor events.

            This trap is driven by 'Blade <framename>/c<1|2> <temp-sensor-name>
            Critical Low Event' event types.

            This trap replaces cBladeHwThreshEvent.

            Severity: 3"

        ::=     { cBladeNotifications 42 }


cBladePowerOnOpEvent NOTIFICATION-TYPE
    OBJECTS {
                cBladeIndex,
                cBladeFrameIndex,
                cBladeName,
                egeneraTrapSeverity,
                egeneraTrapMessage
            }
    STATUS      current
    DESCRIPTION
            "Encapsulates cBlade power on operation event.

            This trap is driven by 'cBlade <framename>/c<1|2> Hardware Operation
            Event' event types.

            Since the underlying event type describes cBlade power on and off
            operation events, enabling/disabling this SNMP trap as an event action
            is bound to the enabling/disabling of cBladePowerOffOpEvent,
            cBladePowerCycleEvent, cBladeResetOpEvent, and cBladeNMIOpEvent.

            Severity: 5"

        ::=     { cBladeNotifications 43 }


cBladePowerOffOpEvent NOTIFICATION-TYPE
    OBJECTS {
                cBladeIndex,
                cBladeFrameIndex,
                cBladeName,
                egeneraTrapSeverity,
                egeneraTrapMessage
            }
    STATUS      current
    DESCRIPTION
            "Encapsulates cBlade power off operation event.

            This trap is driven by 'cBlade <framename>/c<1|2> Hardware Operation
            Event' event types.

            Since the underlying event type describes cBlade power on and off
            operation events, enabling/disabling this SNMP trap as an event action
            is bound to the enabling/disabling of cBladePowerOnOpEvent,
            cBladePowerCycleEvent, cBladeResetOpEvent, and cBladeNMIOpEvent.

            Severity: 5"

        ::=     { cBladeNotifications 44 }


cBladePowerCycleOpEvent NOTIFICATION-TYPE
    OBJECTS {
                cBladeIndex,
                cBladeFrameIndex,
                cBladeName,
                egeneraTrapSeverity,
                egeneraTrapMessage
            }
    STATUS      current
    DESCRIPTION
            "Encapsulates cBlade power cycle operation event.

            This trap is driven by 'cBlade <framename>/c<1|2> Hardware Operation
            Event' event types.

            Since the underlying event type describes cBlade power on and off
            operation events, enabling/disabling this SNMP trap as an event action
            is bound to the enabling/disabling of cBladePowerOnOpEvent,
            cBladePowerCycleEvent, cBladeResetOpEvent, and cBladeNMIOpEvent.

            Severity: 5"

        ::=     { cBladeNotifications 45 }


cBladeResetOpEvent NOTIFICATION-TYPE
    OBJECTS {
                cBladeIndex,
                cBladeFrameIndex,
                cBladeName,
                egeneraTrapSeverity,
                egeneraTrapMessage
            }
    STATUS      current
    DESCRIPTION
            "Encapsulates cBlade reset operation event.

            This trap is driven by 'cBlade <framename>/c<1|2> Hardware Operation
            Event' event types.

            Since the underlying event type describes cBlade power on and off
            operation events, enabling/disabling this SNMP trap as an event action
            is bound to the enabling/disabling of cBladePowerOnOpEvent,
            cBladePowerCycleEvent, cBladePowerCycleOpEvent, and cBladeNMIOpEvent.

            Severity: 5"

        ::=     { cBladeNotifications 46 }


cBladeNMIOpEvent NOTIFICATION-TYPE
    OBJECTS {
                cBladeIndex,
                cBladeFrameIndex,
                cBladeName,
                egeneraTrapSeverity,
                egeneraTrapMessage
            }
    STATUS      current
    DESCRIPTION
            "Encapsulates cBlade reset operation event.

            This trap is driven by 'cBlade <framename>/c<1|2> Hardware Operation
            Event' event types.

            Since the underlying event type describes cBlade power on and off
            operation events, enabling/disabling this SNMP trap as an event action
            is bound to the enabling/disabling of cBladePowerOnOpEvent,
            cBladePowerCycleEvent, cBladePowerCycleOpEvent, and cBladeResetOpEvent.

            Severity: 5"

        ::=     { cBladeNotifications 47 }


cBladeSystemThresholdHighEvent NOTIFICATION-TYPE
    OBJECTS {
                cBladeIndex,
                cBladeFrameIndex,
                cBladeName,
                egeneraTrapSeverity,
                egeneraTrapMessage
            }
    STATUS      current
    DESCRIPTION
            "The notification generated when a cBlade system monitor has
            exceeded its high threshold, or returns below the high threshold.

            This trap is driven by 'cBlade <bladeframe>/c<1|2> <monitorname>
            event' event types.  Note that a severity 3 event is emmitted when
            the threshold is crossed in the rising direction, while a severity
            5 event is emmitted when the monitored value returns below the threshold.
            Thus it is possible to recieve a severity 5 cBladeSystemThresholdHighTrap
            with a message like:

            sagan/c1 5 Minute Load Average returned below 10.0 on average
            for 300 seconds, Current value = 4.79

            Severity: 3/5"

        ::=     { cBladeNotifications 50 }


cBladeNonFatalHwErrorEvent NOTIFICATION-TYPE
    OBJECTS {
                cBladeIndex,
                cBladeFrameIndex,
                cBladeName,
                egeneraTrapSeverity,
                egeneraTrapMessage
            }
    STATUS      current
    DESCRIPTION
            "The notification generated when cBlade hardware detects a non-fatal
            error, such as a correctable ECC memory error.

            This trap is driven by 'cBlade <bladeframe>/c<1|2> NonFatal Hardware
            Error Event' event types.

            Severity: 3"

        ::=     { cBladeNotifications 51 }


cBladeFatalHwErrorEvent NOTIFICATION-TYPE
    OBJECTS {
                cBladeIndex,
                cBladeFrameIndex,
                cBladeName,
                egeneraTrapSeverity,
                egeneraTrapMessage
            }
    STATUS      current
    DESCRIPTION
            "The notification generated when cBlade hardware detects a fatal
            error, such as an uncorrectable ECC memory error.

            This trap is driven by 'cBlade <bladeframe>/c<1|2> Fatal Hardware
            Error Event' event types.

            Severity: 1"

        ::=     { cBladeNotifications 52 }


cBladePanManagerStartedEvent NOTIFICATION-TYPE
    OBJECTS {
                cBladeIndex,
                cBladeFrameIndex,
                cBladeName,
                egeneraTrapSeverity,
                egeneraTrapMessage
            }
    STATUS      current
    DESCRIPTION
            "The notification generated when the PAN Manager has been started
            on a cBlade.

            This trap is driven by 'PAN Manager <bladeframe>/c<1|2> Start Event'
            event types that do not indicate Master or Slave initialization.

            Since the underlying event type describes PAN Manager started and
            master or slave initialization, enabling/disabling this SNMP trap
            as an event action is bound to the enabling/disabling of
            cBladeMasterEvent and cBladeSlaveEvent.

            Severity: 5"

        ::=     { cBladeNotifications 53 }


cBladeNonUniqueDiskIdEvent NOTIFICATION-TYPE
    OBJECTS {
                cBladeIndex,
                cBladeFrameIndex,
                cBladeName,
                diskIdOctets,
                egeneraTrapSeverity,
                egeneraTrapMessage
            }
    STATUS      current
    DESCRIPTION
            "The notification generated when a cBlade detects multiple disks
            with the same Unique ID.

            This trap is driven by 'Non-unique disk ID Event' event types.

            Severity: 1"

        ::=     { cBladeNotifications 54 }


cBladeOutOfServicePendingEvent NOTIFICATION-TYPE
    OBJECTS {
                cBladeIndex,
                cBladeFrameIndex,
                cBladeName,
                egeneraTrapSeverity,
                egeneraTrapMessage
            }
    STATUS      current
    DESCRIPTION
            "The notification generated when a cBlade enters the 'out of service
            pending' state.

            This trap is driven by 'cBlade <bladeframe>/c<1|2> Out of Service Pending
            Event' event types

            Severity: 5"

        ::=     { cBladeNotifications 55 }


cBladeDiskIOAvailableEvent NOTIFICATION-TYPE
    OBJECTS {
                cBladeIndex,
                cBladeFrameIndex,
                cBladeName,
                diskIdOctets,
                diskId,
                egeneraTrapSeverity,
                egeneraTrapMessage
            }
    STATUS      current
    DESCRIPTION
            "The notification generated when disk I/O becomes available on
            a cBlade.

            This trap is driven by 'Device IO Available Event' event types
            that describe Disk I/O availability.

            Severity: 5"

        ::=     { cBladeNotifications 56 }


cBladeDiskIOUnvailableEvent NOTIFICATION-TYPE
    OBJECTS {
                cBladeIndex,
                cBladeFrameIndex,
                cBladeName,
                diskIdOctets,
                diskId,
                egeneraTrapSeverity,
                egeneraTrapMessage
            }
    STATUS      current
    DESCRIPTION
            "The notification generated when disk I/O becomes unavailable on
            a cBlade.

            This trap is driven by 'Device IO Unvailable Event' event types
            that describe disk I/O unavailability.

            Severity: 5"

        ::=     { cBladeNotifications 57 }


cBladeEthIOAvailableEvent NOTIFICATION-TYPE
    OBJECTS {
                cBladeIndex,
                cBladeFrameIndex,
                cBladeName,
                cBladeEthIndex,
                cBladeEthName,
                egeneraTrapSeverity,
                egeneraTrapMessage
            }
    STATUS      current
    DESCRIPTION
            "The notification generated when ethernet I/O becomes available on
            a cBlade.

            This trap is driven by 'Device IO Available Event' event types that
            describe ethernet I/O availability.

            Severity: 5"

        ::=    { cBladeNotifications 58 }


cBladeEthIOUnvailableEvent NOTIFICATION-TYPE
    OBJECTS {
                cBladeIndex,
                cBladeFrameIndex,
                cBladeName,
                cBladeEthIndex,
                cBladeEthName,
                egeneraTrapSeverity,
                egeneraTrapMessage
            }
    STATUS      current
    DESCRIPTION
            "The notification generated when ethernet I/O becomes unavailable on
            a cBlade.

            This trap is driven by 'Device IO Unvailable Event' event types
            that describe ethernet I/O unavailability.

            Severity: 5"

        ::=    { cBladeNotifications 59 }


cBladeCDROMIOAvailableEvent NOTIFICATION-TYPE
    OBJECTS {
                cBladeIndex,
                cBladeFrameIndex,
                cBladeName,
                cdromIdOctets,
                cdromId,
                egeneraTrapSeverity,
                egeneraTrapMessage
            }
    STATUS      current
    DESCRIPTION
            "The notification generated when cd-rom I/O becomes available on
            a cBlade.

            This trap is driven by 'Device IO Available Event' event types that
            describe cd-rom I/O availability.

            Severity: 5"

        ::=    { cBladeNotifications 60 }


cBladeCDROMIOUnvailableEvent NOTIFICATION-TYPE
    OBJECTS {
                cBladeIndex,
                cBladeFrameIndex,
                cBladeName,
                cdromIdOctets,
                cdromId,
                egeneraTrapSeverity,
                egeneraTrapMessage
            }
    STATUS      current
    DESCRIPTION
            "The notification generated when ethernet I/O becomes unavailable on
            a cBlade.

            This trap is driven by 'Device IO Unvailable Event' event types
            that describe ethernet I/O unavailability.

            Severity: 5"

        ::=    { cBladeNotifications 61 }


cBladeEthLinkUpEvent NOTIFICATION-TYPE
    OBJECTS {
                cBladeIndex,
                cBladeFrameIndex,
                cBladeName,
                cBladeEthIndex,
                cBladeEthName,
                egeneraTrapSeverity,
                egeneraTrapMessage
            }
    STATUS      current
    DESCRIPTION
            "The notification generated when a cBlade Eth Link Status is
            detected to be Up.

            This Event is driven by 'ethernet <ethname>@<framename>/c<1|2>
            Link Up Event' event type.

            Severity: 5"

        ::=    { cBladeNotifications 62 }


cBladeEthLinkDownEvent NOTIFICATION-TYPE
    OBJECTS {
                cBladeIndex,
                cBladeFrameIndex,
                cBladeName,
                cBladeEthIndex,
                cBladeEthName,
                egeneraTrapSeverity,
                egeneraTrapMessage
            }
    STATUS      current
    DESCRIPTION
            "The notification generated when a cBlade Eth Link Status is
            detected to be Down.

            This Event is driven by 'ethernet <ethname>@<framename>/c<1|2>
            Link Down Event' event type.

            Severity: 1"

        ::=    { cBladeNotifications 63 }


cBladeEthStatusActiveEvent NOTIFICATION-TYPE
    OBJECTS {
                cBladeIndex,
                cBladeFrameIndex,
                cBladeName,
                cBladeEthIndex,
                cBladeEthName,
                egeneraTrapSeverity,
                egeneraTrapMessage
            }
    STATUS      current
    DESCRIPTION
            "The notification generated when a cBlade Eth Reth Status is
            detected to be Active.

            This Event is driven by 'ethernet <ethname>@<framename>/c<1|2>
            Reth Status Active Event' event type.

            Severity: 5"

        ::=    { cBladeNotifications 64 }


cBladeEthStatusStandbyEvent NOTIFICATION-TYPE
    OBJECTS {
                cBladeIndex,
                cBladeFrameIndex,
                cBladeName,
                cBladeEthIndex,
                cBladeEthName,
                egeneraTrapSeverity,
                egeneraTrapMessage
            }
    STATUS      current
    DESCRIPTION
            "The notification generated when a cBlade Eth Reth Status is
            detected to be Standby.

            This Event is driven by 'ethernet <ethname>@<framename>/c<1|2>
            Reth Status Standby Event' event type.

            Severity: 5"

        ::=    { cBladeNotifications 65 }


cBladeEthStatusFailedEvent NOTIFICATION-TYPE
    OBJECTS {
                cBladeIndex,
                cBladeFrameIndex,
                cBladeName,
                cBladeEthIndex,
                cBladeEthName,
                egeneraTrapSeverity,
                egeneraTrapMessage
            }
    STATUS      current
    DESCRIPTION
            "The notification generated when a cBlade Eth Reth Status is
            detected to be Failed.

            This Event is driven by 'ethernet <ethname>@<framename>/c<1|2>
            Reth Status Failed Event' event type.

            Severity: 2"

        ::=    { cBladeNotifications 66 }


cBladeEthStatusUnconfiguredEvent NOTIFICATION-TYPE
    OBJECTS {
                cBladeIndex,
                cBladeFrameIndex,
                cBladeName,
                cBladeEthIndex,
                cBladeEthName,
                egeneraTrapSeverity,
                egeneraTrapMessage
            }
    STATUS      current
    DESCRIPTION
            "The notification generated when a cBlade Eth Reth Status is
            detected to be Unconfigured (not part of a Reth).  An
            Unconfigured cBlade Eth has Link Status Down.

            This Event is driven by 'ethernet <ethname>@<framename>/c<1|2>
            Reth Status Unconfigured Event' event type.

            Severity: 5"

        ::=    { cBladeNotifications 67 }


cBladeHbaEnabledEvent NOTIFICATION-TYPE
    OBJECTS {
                cBladeIndex,
                cBladeFrameIndex,
                cBladeHbaIndex,
                cBladeHbaName,
                egeneraTrapSeverity,
                egeneraTrapMessage
            }
    STATUS      current
    DESCRIPTION
            "The notification generated when a cBlade HBA set to enabled.

            Severity: 5"

        ::=    { cBladeNotifications 68 }

cBladeHbaDisabledEvent NOTIFICATION-TYPE
    OBJECTS {
                cBladeIndex,
                cBladeFrameIndex,
                cBladeHbaIndex,
                cBladeHbaName,
                egeneraTrapSeverity,
                egeneraTrapMessage
            }
    STATUS      current
    DESCRIPTION
            "The notification generated when a cBlade HBA set to disabled.

            Severity: 3"

        ::=    { cBladeNotifications 69 }

cBladeHbaStatusDownEvent NOTIFICATION-TYPE
    OBJECTS {
                cBladeIndex,
                cBladeFrameIndex,
                cBladeHbaIndex,
                cBladeHbaName,
                egeneraTrapSeverity,
                egeneraTrapMessage
            }
    STATUS      current
    DESCRIPTION
            "The notification generated when a cBlade HBA status is down.

            Severity: 3"

        ::=    { cBladeNotifications 70 }

cBladeHbaStatusChangedEvent NOTIFICATION-TYPE
    OBJECTS {
                cBladeIndex,
                cBladeFrameIndex,
                cBladeHbaIndex,
                cBladeHbaName,
                egeneraTrapSeverity,
                egeneraTrapMessage
            }
    STATUS      current
    DESCRIPTION
            "The notification generated when a cBlade HBA status is changed.

            Severity: 5"

        ::=    { cBladeNotifications 71 }

cBladeFatalSwErrorEvent NOTIFICATION-TYPE
    OBJECTS {
                cBladeIndex,
                cBladeFrameIndex,
                cBladeName,
                egeneraTrapSeverity,
                egeneraTrapMessage
            }
    STATUS      current
    DESCRIPTION
            "The notification generated when cBlade software detects a fatal
            error, such a failure to load required modules.

            Severity: 1"

        ::=    { cBladeNotifications 72 }        


sBladeNotifications OBJECT IDENTIFIER ::= { egeneraNotifications 6 }


sBladeInsertedEvent NOTIFICATION-TYPE
    OBJECTS {
                sBladeIndex,
                sBladeFrameIndex,
                sBladeName,
                egeneraTrapSeverity,
                egeneraTrapMessage
            }
    STATUS      current
    DESCRIPTION
            "The notification generated when an sBlade is inserted into
            a BladeFrame.

            This trap is driven by 'BladeFrame <framename> Blade Inserted Event'
            event types that describe sBlade insertions.

            Since the underlying event type describes pBlade, cBlade, and sBlade
            insertions, enabling/disabling this SNMP trap as an event action is
            bound to the enabling/disabling of pBladeInsertedEvent and
            cBladeInsertedEvent.

            Since BladeFrame ES Systems do not utilize dedicated sBlades, this
            trap is not relevant to BladeFrame ES systems.

            Severity: 5"

        ::=     { sBladeNotifications 1 }


sBladeRemovedEvent NOTIFICATION-TYPE
    OBJECTS {
                sBladeIndex,
                sBladeFrameIndex,
                sBladeName,
                egeneraTrapSeverity,
                egeneraTrapMessage
            }
    STATUS      current
    DESCRIPTION
            "The notification generated when an sBlade is inserted into
            a BladeFrame.

            This trap is driven by 'BladeFrame <framename> Blade Inserted Event'
            event types that describe sBlade insertions.

            Since the underlying event type describes pBlade, cBlade, and sBlade
            insertions, enabling/disabling this SNMP trap as an event action is
            bound to the enabling/disabling of pBladeInsertedEvent and
            cBladeInsertedEvent.

            Since BladeFrame ES Systems do not utilize dedicated sBlades, this
            trap is not relevant to BladeFrame ES systems.

            Severity: 5"

        ::=     { sBladeNotifications 2 }


sBladePowerOnEvent NOTIFICATION-TYPE
    OBJECTS {
                sBladeIndex,
                sBladeFrameIndex,
                sBladeName,
                egeneraTrapSeverity,
                egeneraTrapMessage
            }
    STATUS      current
    DESCRIPTION
            "The notification generated when an sBlade is powered on.

            This trap is driven by 'Blade <framename>/s<1|2> Power Status Event'
            event types describing power on events.

            Since the underlying event type describes sBlade power on and off
            events, enabling/disabling this SNMP trap as an event action is bound
            to the enabling/disabling of sBladePowerOffEvent.

            Since BladeFrame ES Systems do not utilize dedicated sBlades, this
            trap is not relevant to BladeFrame ES systems.  BladeFrame ES systems
            emit the cBladeSwitchCardOnEvent to indicate the switch card of the
            cBlade has been powered on.

            Severity: 5"

        ::=     { sBladeNotifications 3 }


sBladePowerOffEvent NOTIFICATION-TYPE
    OBJECTS {
                sBladeIndex,
                sBladeFrameIndex,
                sBladeName,
                egeneraTrapSeverity,
                egeneraTrapMessage
            }
    STATUS      current
    DESCRIPTION
            "The notification generated when an sBlade is powered off.

            This trap is driven by 'Blade <framename>/s<1|2> Power Status Event'
            event types describing power on events.

            Since the underlying event type describes sBlade power on and off
            events, enabling/disabling this SNMP trap as an event action is bound
            to the enabling/disabling of sBladePowerOnEvent.

            Since BladeFrame ES Systems do not utilize dedicated sBlades, this
            trap is not relevant to BladeFrame ES systems.  BladeFrame ES systems
            emit the cBladeSwitchCardOffEvent to indicate the switch card of the
            cBlade has been powered off.

            Severity: 5"

        ::=     { sBladeNotifications 4 }


sBladeEnabledEvent NOTIFICATION-TYPE
    OBJECTS {
                sBladeIndex,
                sBladeFrameIndex,
                sBladeName,
                egeneraTrapSeverity,
                egeneraTrapMessage
            }
    STATUS      current
    DESCRIPTION
            "The notification generated when an sBlade is enabled (returns
             to service).

             This trap is driven by 'Blade <framename>/s<1|2> Out of Service Status
             false Event' event types.

             Since BladeFrame ES Systems do not utilize dedicated sBlades, this
             trap is not relevant to BladeFrame ES systems.

             Severity: 5"

        ::=     { sBladeNotifications 5 }


sBladeDisabledEvent NOTIFICATION-TYPE
    OBJECTS {
                sBladeIndex,
                sBladeFrameIndex,
                sBladeName,
                egeneraTrapSeverity,
                egeneraTrapMessage
            }
    STATUS      current
    DESCRIPTION
            "The notification generated when an SBlade is disabled. (removed
             from service).

             This trap is driven by 'Blade <framename>/s<1|2> Out of Service Status
             true Event' event types.

             Since BladeFrame ES Systems do not utilize dedicated sBlades, this
             trap is not relevant to BladeFrame ES systems.

             Severity: 5"

        ::=     { sBladeNotifications 6 }


sBladeSelectedEvent NOTIFICATION-TYPE
    OBJECTS {
                sBladeIndex,
                sBladeFrameIndex,
                sBladeName,
                egeneraTrapSeverity,
                egeneraTrapMessage
            }
    STATUS      current
    DESCRIPTION
            "The notification generated when an sBlade has been
             selected.

             This trap is driven by 'Blade <framename>/s<1|2> Selected Status
             true Event' even types.

             Since BladeFrame ES Systems do not utilize dedicated sBlades, this
             trap is not relevant to BladeFrame ES systems.

             Severity: 5"

        ::=     { sBladeNotifications 7 }


sBladeDeselectedEvent NOTIFICATION-TYPE
    OBJECTS {
                sBladeIndex,
                sBladeFrameIndex,
                sBladeName,
                egeneraTrapSeverity,
                egeneraTrapMessage
            }
    STATUS      current
    DESCRIPTION
            "The notification generated when a sBlade has been
             de-selected.

             This trap is driven by 'Blade <framename>/s<1|2> Selected Status
             false Event' even types.

             Since BladeFrame ES Systems do not utilize dedicated sBlades, this
             trap is not relevant to BladeFrame ES systems.

             Severity: 5"

        ::=     { sBladeNotifications 8 }


--sBladeHwThreshEvent NOTIFICATION-TYPE
--    OBJECTS {
--                sBladeIndex,
--                sBladeFrameIndex,
--                sBladeName,
--                hwTheshComponent,
--                hwTheshLevel,
--                egeneraTrapSeverity,
--                egeneraTrapMessage
--            }
--    STATUS      current
--    DESCRIPTION
--            "Encapsulates hardward threshold events.
--
--            This trap has been deprecated in favor of sBladeVoltageUpperTrap,
--            sBladeVoltageLowerTrap, sBladeFanSpeedUpperTrap, sBladeFanSpeedLowerTrap,
--            sBladeTempUpperTrap, and sBladeTempLowerTrap."
--
--        ::=     { sBladeNotifications 9 }


sBladeHwEvent NOTIFICATION-TYPE
    OBJECTS {
                sBladeIndex,
                sBladeFrameIndex,
                sBladeName,
                egeneraTrapSeverity,
                egeneraTrapMessage
            }
    STATUS      current
    DESCRIPTION
            "Encapsulates generic events from hardware.

             This trap is driven by 'Blade <framename>/s<1|2> non-sensor
             Event' event types Examples message contents include:

             bmc reset

             Contact EES for more specific information.

             Since BladeFrame ES Systems do not utilize dedicated sBlades, this
             trap is not relevant to BladeFrame ES systems.

             Severity: 3"

        ::=     { sBladeNotifications 10 }


sBladeVoltageUpperEvent NOTIFICATION-TYPE
    OBJECTS {
                sBladeIndex,
                sBladeFrameIndex,
                sBladeName,
                sensorName,
                sensorThreshold,
                sensorValue,
                egeneraTrapSeverity,
                egeneraTrapMessage
            }
    STATUS      current
    DESCRIPTION
            "Encapsulates sBlade critical high voltage sensor events.

             This trap is driven by 'Blade <framename>/s<1|2> <voltage-sensor-name>
             Critical High Event' event types.

             The sensorValue and sensorThreshold fields are ingeter representations
             of real numbers.  The real numbers are multiplied by 100 and rounded
             to produce an integer, thus 0.530 => 53.

             This trap replaces sBladeHwThreshEvent.

             Since BladeFrame ES Systems do not utilize dedicated sBlades, this
             trap is not relevant to BladeFrame ES systems.

             Severity: 3"

        ::=     { sBladeNotifications 11 }


sBladeVoltageLowerEvent NOTIFICATION-TYPE
    OBJECTS {
                sBladeIndex,
                sBladeFrameIndex,
                sBladeName,
                sensorName,
                sensorThreshold,
                sensorValue,
                egeneraTrapSeverity,
                egeneraTrapMessage
            }
    STATUS      current
    DESCRIPTION
            "Encapsulates sBlade critical low voltage sensor events.

             This trap is driven by 'Blade <framename>/s<1|2> <voltage-sensor-name>
             Critical Low Event' event types.

             The sensorValue and sensorThreshold fields are ingeter representations
             of real numbers.  The real numbers are multiplied by 100 and rounded
             to produce an integer, thus 0.530 => 53.

             This trap replaces sBladeHwThreshEvent.

             Since BladeFrame ES Systems do not utilize dedicated sBlades, this
             trap is not relevant to BladeFrame ES systems.

             Severity: 3"

        ::=     { sBladeNotifications 12 }


sBladeFanSpeedUpperEvent NOTIFICATION-TYPE
    OBJECTS {
                sBladeIndex,
                sBladeFrameIndex,
                sBladeName,
                sensorName,
                sensorThreshold,
                sensorValue,
                egeneraTrapSeverity,
                egeneraTrapMessage
            }
    STATUS      current
    DESCRIPTION
            "Encapsulates sBlade critical high fan speed  sensor events.

             This trap is driven by 'Blade <framename>/s<1|2> <fan-sensor-name>
             Critical High Event' event types.

             This trap replaces sBladeHwThreshEvent.

             Since BladeFrame ES Systems do not utilize dedicated sBlades, this
             trap is not relevant to BladeFrame ES systems.

             Severity: 3"

        ::=     { sBladeNotifications 13 }


sBladeFanSpeedLowerEvent NOTIFICATION-TYPE
    OBJECTS {
                sBladeIndex,
                sBladeFrameIndex,
                sBladeName,
                sensorName,
                sensorThreshold,
                sensorValue,
                egeneraTrapSeverity,
                egeneraTrapMessage
            }
    STATUS      current
    DESCRIPTION
            "Encapsulates sBlade critical low fan speed sensor events.

             This trap is driven by 'Blade <framename>/s<1|2> <fan-sensor-name>
             Critical Low Event' event types.

             This trap replaces sBladeHwThreshEvent.

             Since BladeFrame ES Systems do not utilize dedicated sBlades, this
             trap is not relevant to BladeFrame ES systems.

             Severity: 3"

        ::=     { sBladeNotifications 14 }



sBladeTempUpperEvent NOTIFICATION-TYPE
    OBJECTS {
                sBladeIndex,
                sBladeFrameIndex,
                sBladeName,
                sensorName,
                sensorThreshold,
                sensorValue,
                egeneraTrapSeverity,
                egeneraTrapMessage
            }
    STATUS      current
    DESCRIPTION
            "Encapsulates cBlade critical high temperature sensor events.

             This trap is driven by 'Blade <framename>/s<1|2> <temp-sensor-name>
             Critical High Event' event types.

             This trap replaces sBladeHwThreshEvent.

             Since BladeFrame ES Systems do not utilize dedicated sBlades, this
             trap is not relevant to BladeFrame ES systems.

             Severity: 3"

        ::=     { sBladeNotifications 15 }


sBladeTempLowerEvent NOTIFICATION-TYPE
    OBJECTS {
                sBladeIndex,
                sBladeFrameIndex,
                sBladeName,
                sensorName,
                sensorThreshold,
                sensorValue,
                egeneraTrapSeverity,
                egeneraTrapMessage
            }
    STATUS      current
    DESCRIPTION
            "Encapsulates sBlade critical low temperature sensor events.

             This trap is driven by 'Blade <framename>/s<1|2> <temp-sensor-name>
             Critical Low Event' event types.

             This trap replaces sBladeHwThreshEvent.

             Since BladeFrame ES Systems do not utilize dedicated sBlades, this
             trap is not relevant to BladeFrame ES systems.

             Severity: 3"

        ::=     { sBladeNotifications 16 }


sBladePowerOnOpEvent NOTIFICATION-TYPE
    OBJECTS {
                sBladeIndex,
                sBladeFrameIndex,
                sBladeName,
                egeneraTrapSeverity,
                egeneraTrapMessage
            }
    STATUS      current
    DESCRIPTION
            "Encapsulates sBlade power on operation event.

            This trap is driven by 'sBlade <framename>/s<1|2> Hardware Operation
            Event' event types.

            Since the underlying event type describes sBlade power on and off
            operation events, enabling/disabling this SNMP trap as an event action
            is bound to the enabling/disabling of sBladePowerOffOpEvent,
            sBladePowerCycleEvent, and sBladeResetOpEvent.

            Severity: 5"

        ::=     { sBladeNotifications 17 }


sBladePowerOffOpEvent NOTIFICATION-TYPE
    OBJECTS {
                sBladeIndex,
                sBladeFrameIndex,
                sBladeName,
                egeneraTrapSeverity,
                egeneraTrapMessage
            }
    STATUS      current
    DESCRIPTION
            "Encapsulates sBlade power off operation event.

            This trap is driven by 'sBlade <framename>/s<1|2> Hardware Operation
            Event' event types.

            Since the underlying event type describes sBlade power on and off
            operation events, enabling/disabling this SNMP trap as an event action
            is bound to the enabling/disabling of sBladePowerOnOpEvent,
            sBladePowerCycleEvent, and sBladeResetOpEvent.

            Severity: 5"

        ::=     { sBladeNotifications 18 }


sBladePowerCycleOpEvent NOTIFICATION-TYPE
    OBJECTS {
                sBladeIndex,
                sBladeFrameIndex,
                sBladeName,
                egeneraTrapSeverity,
                egeneraTrapMessage
            }
    STATUS      current
    DESCRIPTION
            "Encapsulates sBlade power cycle operation event.

            This trap is driven by 'sBlade <framename>/s<1|2> Hardware Operation
            Event' event types.

            Since the underlying event type describes sBlade power on and off
            operation events, enabling/disabling this SNMP trap as an event action
            is bound to the enabling/disabling of sBladePowerOnOpEvent,
            sBladePowerCycleEvent, and sBladeResetOpEvent.

            Severity: 5"

        ::=     { sBladeNotifications 19 }


sBladeResetOpEvent NOTIFICATION-TYPE
    OBJECTS {
                sBladeIndex,
                sBladeFrameIndex,
                sBladeName,
                egeneraTrapSeverity,
                egeneraTrapMessage
            }
    STATUS      current
    DESCRIPTION
            "Encapsulates sBlade reset operation event.

            This trap is driven by 'sBlade <framename>/s<1|2> Hardware Operation
            Event' event types.

            Since the underlying event type describes sBlade power on and off
            operation events, enabling/disabling this SNMP trap as an event action
            is bound to the enabling/disabling of sBladePowerOnOpEvent,
            sBladePowerCycleEvent, and sBladePowerCycleOpEvent.

            Severity: 5"

        ::=     { sBladeNotifications 20 }


sBladeNonFatalHwErrorEvent NOTIFICATION-TYPE
    OBJECTS {
                sBladeIndex,
                sBladeFrameIndex,
                sBladeName,
                egeneraTrapSeverity,
                egeneraTrapMessage
            }
    STATUS      current
    DESCRIPTION
            "The notification generated when sBlade hardware detects a non-fatal
            error.

            This trap is driven by 'sBlade <bladeframe>/s<1|2> NonFatal Hardware
            Error Event' event types.

            Severity: 3"

        ::=     { sBladeNotifications 21 }


sBladeFatalHwErrorEvent NOTIFICATION-TYPE
    OBJECTS {
                sBladeIndex,
                sBladeFrameIndex,
                sBladeName,
                egeneraTrapSeverity,
                egeneraTrapMessage
            }
    STATUS      current
    DESCRIPTION
            "The notification generated when sBlade hardware detects a fatal
            error.

            This trap is driven by 'sBlade <bladeframe>/s<1|2> Fatal Hardware
            Error Event' event types.

            Severity: 1"

        ::=     { sBladeNotifications 22 }


sBladeOutOfServicePendingEvent NOTIFICATION-TYPE
    OBJECTS {
                sBladeIndex,
                sBladeFrameIndex,
                sBladeName,
                egeneraTrapSeverity,
                egeneraTrapMessage
            }
    STATUS      current
    DESCRIPTION
            "The notification generated when a sBlade enters the 'out of service
            pending' state.

            This trap is driven by 'cBlade <bladeframe>/s<1|2> Out of Service Pending
            Event' event types

            Severity: 5"

        ::=     { sBladeNotifications 23 }



pBladeNotifications OBJECT IDENTIFIER ::= { egeneraNotifications 7 }


pBladeInsertedEvent NOTIFICATION-TYPE
    OBJECTS {
                pBladeIndex,
                pBladeFrameIndex,
                pBladeName,
                egeneraTrapSeverity,
                egeneraTrapMessage
            }
    STATUS      current
    DESCRIPTION
            "The notification generated when a pBlade is inserted into
            a BladeFrame.

            This trap is driven by 'BladeFrame <framename> Blade Inserted Event'
            event types that describe pBlade insertions.

            Since the underlying event type describes pBlade, cBlade, and sBlade
            insertions, enabling/disabling this SNMP trap as an event action is
            bound to the enabling/disabling of sBladeInsertedEvent and
            cBladeInsertedEvent.

            Severity: 5"

        ::=     { pBladeNotifications 1 }


pBladeRemovedEvent NOTIFICATION-TYPE
    OBJECTS {
                pBladeIndex,
                pBladeFrameIndex,
                pBladeName,
                egeneraTrapSeverity,
                egeneraTrapMessage
            }
    STATUS      current
    DESCRIPTION
            "The notification generated when a pBlade is removed from
            a BladeFrame.

            This trap is driven by 'BladeFrame <framename> Blade Removed Event'
            event types that describe pBlade removal events.

            Since the underlying event type describes pBlade, cBlade, and sBlade
            removal, enabling/disabling this SNMP trap as an event action is
            bound to the enabling/disabling of sBladeRemovedEvent and
            cBladeRemovedEvent.

            Severity: 3"

        ::=     { pBladeNotifications 2 }


pBladePowerOnEvent NOTIFICATION-TYPE
    OBJECTS {
                pBladeIndex,
                pBladeFrameIndex,
                pBladeName,
                egeneraTrapSeverity,
                egeneraTrapMessage
            }
    STATUS      current
    DESCRIPTION
            "The notification generated when a pBlade is powered on.

            This trap is driven by 'Blade <framename>/p<1|2> Power Status Event'
            event types describing power on events.

            Since the underlying event type describes pBlade power on and off
            events, enabling/disabling this SNMP trap as an event action is bound
            to the enabling/disabling of pBladePowerOffEvent.

            Severity: 5"

        ::=     { pBladeNotifications 3 }


pBladePowerOffEvent NOTIFICATION-TYPE
    OBJECTS {
                pBladeIndex,
                pBladeFrameIndex,
                pBladeName,
                egeneraTrapSeverity,
                egeneraTrapMessage
            }
    STATUS      current
    DESCRIPTION
            "The notification generated when a pBlade is powered off.

            This trap is driven by 'Blade <framename>/p<1|2> Power Status Event'
            event types describing power on events.

            Since the underlying event type describes sBlade power on and off
            events, enabling/disabling this SNMP trap as an event action is bound
            to the enabling/disabling of pBladePowerOnEvent.

            Severity: 5"

        ::=     { pBladeNotifications 4 }


pBladeBootedEvent NOTIFICATION-TYPE
    OBJECTS {
                pBladeIndex,
                pBladeFrameIndex,
                pBladeName,
                egeneraTrapSeverity,
                egeneraTrapMessage
            }
    STATUS      current
    DESCRIPTION
            "The notification generated when a pBlade has successfully
            booted.

            This trap is driven by 'blade.status.monitor.event' event types
            that describe a pBlade transition from the booting state to the
            running state.

            This event type is not user visible, and will not appear in
            CLI or GUI event queries.  The trap exists to satisfy early
            requirements documents.

            Severity: 5"

        ::=     { pBladeNotifications 5 }


pBladeShutdownEvent NOTIFICATION-TYPE
    OBJECTS {
                pBladeIndex,
                pBladeFrameIndex,
                pBladeName,
                egeneraTrapSeverity,
                egeneraTrapMessage
            }
    STATUS      current
    DESCRIPTION
            "The notification generated when a pBlade has been shut
             down.

            This trap is driven by 'blade.status.monitor.event' event types
            that describe a pBlade transition from the shutting down state to
            the shutdown state.

            This event type is not user visible, and will not appear in
            CLI or GUI event queries.  The trap exists to satisfy early
            requirements documents.

            Severity: 5"

        ::=     { pBladeNotifications 6 }


pBladeEnabledEvent NOTIFICATION-TYPE
    OBJECTS {
                pBladeIndex,
                pBladeFrameIndex,
                pBladeName,
                egeneraTrapSeverity,
                egeneraTrapMessage
            }
    STATUS      current
    DESCRIPTION
            "The notification generated when a pBlade has been enabled
             (returns to service).

             This trap is driven by 'Blade <framename>/p<1..24> Out of Service Status
             false Event' event types.

             Severity: 5"

        ::=     { pBladeNotifications 7 }


pBladeDisabledEvent NOTIFICATION-TYPE
    OBJECTS {
                pBladeIndex,
                pBladeFrameIndex,
                pBladeName,
                egeneraTrapSeverity,
                egeneraTrapMessage
            }
    STATUS      current
    DESCRIPTION
            "The notification generated when a pBlade has been disabled
             (removed from service).

             This trap is driven by 'Blade <framename>/p<1..24> Out of Service Status
             true Event' event types.

             Severity: 5"

        ::=     { pBladeNotifications 8 }


pBladeSelectedEvent NOTIFICATION-TYPE
    OBJECTS {
                pBladeIndex,
                pBladeFrameIndex,
                pBladeName,
                egeneraTrapSeverity,
                egeneraTrapMessage
            }
    STATUS      current
    DESCRIPTION
            "The notification generated when a pBlade has been selected.

             This trap is driven by 'Blade <framename>/p<1..24> Selected Status
             true Event' even types.

             Severity: 5"

        ::=     { pBladeNotifications 9 }


pBladeDeselectedEvent NOTIFICATION-TYPE
    OBJECTS {
                pBladeIndex,
                pBladeFrameIndex,
                pBladeName,
                egeneraTrapSeverity,
                egeneraTrapMessage
            }
    STATUS      current
    DESCRIPTION
            "The notification generated when a pBlade has been unselected.

             This trap is driven by 'Blade <framename>/p<1..24> Selected Status
             false Event' even types.

             Severity: 5"

        ::=     { pBladeNotifications 10 }


pBladeHwEvent NOTIFICATION-TYPE
    OBJECTS {
                pBladeIndex,
                pBladeFrameIndex,
                pBladeName,
                egeneraTrapSeverity,
                egeneraTrapMessage
            }
    STATUS      current
    DESCRIPTION
            "Encapsulates generic events from hardware.

            This trap is driven by 'Blade <framename>/p<1..24> non-sensor Event'
            event types that do not indicate panic, commanded shutdown,
            commanded reboot, or init level events.  Examples message contents
            include:

            OEM Type 0xe0, value = 0x64:0x21:0xce:0xe0:0x1d:0x00:0x00:0x00...
            bmc reset
            deasserted, value = 0x0211
            system booted

            Contact EES for more specific information.

            Since the underlying event type describes pBlade all non-sensor hardware
            events, and since there are specific traps for panic, commanded shutdown,
            commanded reboot, and init level events, enabling/disabling this SNMP trap
            as an event action is bound to the enabling/disabling of pBladePanicEvent,
            pBladeCmdShutdownEvent, pBladeCmdRebootEvent, pBladeCmdHaltEvent, and
            pBladeInitEvent.

            Severity: 3"

        ::=     { pBladeNotifications 11 }

--pBladeHwThreshEvent NOTIFICATION-TYPE
--    OBJECTS {
--                pBladeIndex,
--                pBladeFrameIndex,
--                pBladeName,
--                hwTheshComponent,
--                hwTheshLevel,
--                egeneraTrapSeverity,
--                egeneraTrapMessage
--            }
--    STATUS      current
--    DESCRIPTION
--            "Encapsulates hardward threshold events.
--
--            This trap has been deprecated in favor of pBladeVoltageUpperEvent,
--            pBladeVoltageLowerEvent, pBladeFanSpeedUpperEvent, pBladeFanSpeedLowerEvent,
--            pBladeTempUpperEvent, and pBladeTempLowerEvent."
--
--        ::=     { pBladeNotifications 12 }


pBladePanicEvent NOTIFICATION-TYPE
    OBJECTS {
                pBladeIndex,
                pBladeFrameIndex,
                pBladeName,
                egeneraTrapSeverity,
                egeneraTrapMessage
            }
    STATUS      current
    DESCRIPTION
            "Encapsulates hardware events identifying pBlade panics that
            cause the cBlade to enter KDB, reboot, or halt'

            This trap is driven by 'Blade <framename>/p<1..24> non-sensor Event'
            event types that describe kernel panics.

            Contact EES for more specific information.

            Since the underlying event type describes pBlade non-sensor hardware
            events, and since there are specific traps for panic, commanded shutdown,
            commanded reboot, and init level events, enabling/disabling this SNMP trap
            as an event action is bound to the enabling/disabling of pBladeHwEventEvent,
            pBladeCmdShutdownEvent, pBladeCmdRebootEvent, pBladeCmdHaltEvent, and
            pBladeInitEvent.

            Severity: 3"

        ::=     { pBladeNotifications 13 }


pBladeCmdHaltEvent NOTIFICATION-TYPE
    OBJECTS {
                pBladeIndex,
                pBladeFrameIndex,
                pBladeName,
                egeneraTrapSeverity,
                egeneraTrapMessage
            }
    STATUS      current
    DESCRIPTION
            "Encapsulates hardware events indicating intentional pBlade
            halt.

            This trap is driven by 'Blade <framename>/p<1..24> non-sensor Event'
            event types that describe commanded halts.

            Contact EES for more specific information.

            Since the underlying event type describes pBlade non-sensor hardware
            events, and since there are specific traps for panic, commanded shutdown,
            commanded reboot, and init level events, enabling/disabling this SNMP trap
            as an event action is bound to the enabling/disabling of pBladeHwEventEvent,
            pBladeCmdShutdownEvent, pBladeCmdRebootEvent, pBladePanicEvent, and
            pBladeInitEvent.

            Severity: 3"

        ::=     { pBladeNotifications 16 }


pBladeCmdRebootEvent NOTIFICATION-TYPE
    OBJECTS {
                pBladeIndex,
                pBladeFrameIndex,
                pBladeName,
                egeneraTrapSeverity,
                egeneraTrapMessage
            }
    STATUS      current
    DESCRIPTION
            "Encapsulates hardware events indicating intentional pBlade
            reboot.

            This trap is driven by 'Blade <framename>/p<1..24> non-sensor Event'
            event types that describe commanded reboots.

            Contact EES for more specific information.

            Since the underlying event type describes pBlade non-sensor hardware
            events, and since there are specific traps for panic, commanded shutdown,
            commanded reboot, and init level events, enabling/disabling this SNMP trap
            as an event action is bound to the enabling/disabling of pBladeHwEventTrap,
            pBladeCmdShutdownTrap, pBladeCmdHaltTrap, pBladePanicTrap, and
            pBladeInitTrap.

            Severity: 3"

        ::=     { pBladeNotifications 17 }


pBladeInitEvent NOTIFICATION-TYPE
    OBJECTS {
                pBladeIndex,
                pBladeFrameIndex,
                pBladeName,
                egeneraTrapSeverity,
                egeneraTrapMessage
            }
    STATUS      current
    DESCRIPTION
            "Encapsulates hardware events indicating intentional pBlade
            has reached an init level.

            This trap is driven by 'Blade <framename>/p<1..24> non-sensor Event'
            event types that describe init level reached.

            Contact EES for more specific information.

            Since the underlying event type describes pBlade non-sensor hardware
            events, and since there are specific traps for panic, commanded shutdown,
            commanded reboot, and init level events, enabling/disabling this SNMP trap
            as an event action is bound to the enabling/disabling of pBladeHwEventEvent,
            pBladeCmdShutdownEvent, pBladeCmdHaltEvent, pBladeCmdRebootEvent, and
            pBladePanicEvent.

            Severity: 3"

        ::=     { pBladeNotifications 18 }



pBladeVoltageUpperEvent NOTIFICATION-TYPE
    OBJECTS {
                pBladeIndex,
                pBladeFrameIndex,
                pBladeName,
                sensorName,
                sensorThreshold,
                sensorValue,
                egeneraTrapSeverity,
                egeneraTrapMessage
            }
    STATUS      current
    DESCRIPTION
            "Encapsulates pBlade critical high voltage sensor events.

            This trap is driven by 'Blade <framename>/p<1..24> <voltage-sensor-name>
            Critical High Event' event types.

            The sensorValue and sensorThreshold fields are ingeter representations
            of real numbers.  The real numbers are multiplied by 100 and rounded
            to produce an integer, thus 0.530 => 53.

            This trap replaces pBladeHwThreshEvent.

            Severity: 3"

        ::=     { pBladeNotifications 19 }


pBladeVoltageLowerEvent NOTIFICATION-TYPE
    OBJECTS {
                pBladeIndex,
                pBladeFrameIndex,
                pBladeName,
                sensorName,
                sensorThreshold,
                sensorValue,
                egeneraTrapSeverity,
                egeneraTrapMessage
            }
    STATUS      current
    DESCRIPTION
            "Encapsulates pBlade critical low voltage sensor events.

            This trap is driven by 'Blade <framename>/p<1..24> <voltage-sensor-name>
            Critical Low Event' event types.

            The sensorValue and sensorThreshold fields are ingeter representations
            of real numbers.  The real numbers are multiplied by 100 and rounded
            to produce an integer, thus 0.530 => 53.

            This trap replaces pBladeHwThreshEvent.

            Severity: 3"

        ::=     { pBladeNotifications 20 }


pBladeFanSpeedUpperEvent NOTIFICATION-TYPE
    OBJECTS {
                pBladeIndex,
                pBladeFrameIndex,
                pBladeName,
                sensorName,
                sensorThreshold,
                sensorValue,
                egeneraTrapSeverity,
                egeneraTrapMessage
            }
    STATUS      current
    DESCRIPTION
            "Encapsulates pBlade critical high fan speed  sensor events.

            This trap is driven by 'Blade <framename>/p<1..24> <fan-sensor-name>
            Critical High Event' event types.

            This trap replaces pBladeHwThreshEvent.

            Severity: 3"

        ::=     { pBladeNotifications 21 }


pBladeFanSpeedLowerEvent NOTIFICATION-TYPE
    OBJECTS {
                pBladeIndex,
                pBladeFrameIndex,
                pBladeName,
                sensorName,
                sensorThreshold,
                sensorValue,
                egeneraTrapSeverity,
                egeneraTrapMessage
            }
    STATUS      current
    DESCRIPTION
            "Encapsulates pBlade critical low fan speed sensor events.

            This trap is driven by 'Blade <framename>/p<1..24> <fan-sensor-name>
            Critical Low Event' event types.

            This trap replaces pBladeHwThreshEvent.

            Severity: 3"

        ::=     { pBladeNotifications 22 }



pBladeTempUpperEvent NOTIFICATION-TYPE
    OBJECTS {
                pBladeIndex,
                pBladeFrameIndex,
                pBladeName,
                sensorName,
                sensorThreshold,
                sensorValue,
                egeneraTrapSeverity,
                egeneraTrapMessage
            }
    STATUS      current
    DESCRIPTION
            "Encapsulates pBlade critical high temperature sensor events.

            This trap is driven by 'Blade <framename>/p<1..24> <temp-sensor-name>
            Critical High Event' event types.

            This trap replaces pBladeHwThreshEvent.

            Severity: 3"

        ::=     { pBladeNotifications 23 }


pBladeTempLowerEvent NOTIFICATION-TYPE
    OBJECTS {
                pBladeIndex,
                pBladeFrameIndex,
                pBladeName,
                sensorName,
                sensorThreshold,
                sensorValue,
                egeneraTrapSeverity,
                egeneraTrapMessage
            }
    STATUS      current
    DESCRIPTION
            "Encapsulates pBlade critical low temperature sensor events.

            This trap is driven by 'Blade <framename>/p<1..24> <temp-sensor-name>
            Critical Low Event' event types.

            This trap replaces pBladeHwThreshEvent.

            Severity: 3"

        ::=     { pBladeNotifications 24 }


pBladeWinkoutEvent NOTIFICATION-TYPE
    OBJECTS {
                pBladeIndex,
                pBladeFrameIndex,
                pBladeName,
                egeneraTrapSeverity,
                egeneraTrapMessage
            }
    STATUS      current
    DESCRIPTION
            "Encapsulates pBlade wink-out events..

            This trap is driven by 'pBlade <framename>/p<1..24> Winked Out Event
            event types.

            Severity: 3"

        ::=     { pBladeNotifications 25 }



pBladePowerOnOpEvent NOTIFICATION-TYPE
    OBJECTS {
                pBladeIndex,
                pBladeFrameIndex,
                pBladeName,
                egeneraTrapSeverity,
                egeneraTrapMessage
            }
    STATUS      current
    DESCRIPTION
            "Encapsulates pBlade power on operation event.

            This trap is driven by 'pBlade <framename>/p<1..24> Hardware Operation
            Event' event types.

            Since the underlying event type describes pBlade power on and off
            operation events, enabling/disabling this SNMP trap as an event action
            is bound to the enabling/disabling of pBladePowerOffOpEvent,
            pBladePowerCycleEvent, pBladeResetOpEvent, and pBladeNMIOpEvent.

            Severity: 5"

        ::=     { pBladeNotifications 26 }


pBladePowerOffOpEvent NOTIFICATION-TYPE
    OBJECTS {
                pBladeIndex,
                pBladeFrameIndex,
                pBladeName,
                egeneraTrapSeverity,
                egeneraTrapMessage
            }
    STATUS      current
    DESCRIPTION
            "Encapsulates pBlade power off operation event.

            This trap is driven by 'pBlade <framename>/p<1..24> Hardware Operation
            Event' event types.

            Since the underlying event type describes pBlade power on and off
            operation events, enabling/disabling this SNMP trap as an event action
            is bound to the enabling/disabling of pBladePowerOnOpEvent,
            pBladePowerCycleEvent, pBladeResetOpEvent, and pBladeNMIOpEvent.

            Severity: 5"

        ::=     { pBladeNotifications 27 }


pBladePowerCycleOpEvent NOTIFICATION-TYPE
    OBJECTS {
                pBladeIndex,
                pBladeFrameIndex,
                pBladeName,
                egeneraTrapSeverity,
                egeneraTrapMessage
            }
    STATUS      current
    DESCRIPTION
            "Encapsulates pBlade power cycle operation event.

            This trap is driven by 'pBlade <framename>/p<1..24> Hardware Operation
            Event' event types.

            Since the underlying event type describes pBlade power on and off
            operation events, enabling/disabling this SNMP trap as an event action
            is bound to the enabling/disabling of pBladePowerOnOpEvent,
            pBladePowerCycleEvent, pBladeResetOpEvent, and pBladeNMIOpEvent.

            Severity: 5"

        ::=     { pBladeNotifications 28 }


pBladeResetOpEvent NOTIFICATION-TYPE
    OBJECTS {
                pBladeIndex,
                pBladeFrameIndex,
                pBladeName,
                egeneraTrapSeverity,
                egeneraTrapMessage
            }
    STATUS      current
    DESCRIPTION
            "Encapsulates pBlade reset operation event.

            This trap is driven by 'pBlade <framename>/p<1..24> Hardware Operation
            Event' event types.

            Since the underlying event type describes pBlade power on and off
            operation events, enabling/disabling this SNMP trap as an event action
            is bound to the enabling/disabling of pBladePowerOnOpEvent,
            pBladePowerCycleEvent, pBladePowerCycleOpEvent, and pBladeNMIOpEvent.

            Severity: 5"

        ::=     { pBladeNotifications 29 }


pBladeNMIOpEvent NOTIFICATION-TYPE
    OBJECTS {
                pBladeIndex,
                pBladeFrameIndex,
                pBladeName,
                egeneraTrapSeverity,
                egeneraTrapMessage
            }
    STATUS      current
    DESCRIPTION
            "Encapsulates pBlade reset operation event.

            This trap is driven by 'pBlade <framename>/p<1..24> Hardware Operation
            Event' event types.

            Since the underlying event type describes pBlade power on and off
            operation events, enabling/disabling this SNMP trap as an event action
            is bound to the enabling/disabling of pBladePowerOnOpEvent,
            pBladePowerCycleEvent, pBladePowerCycleOpEvent, and pBladeResetOpEvent.

            Severity: 5"

        ::=     { pBladeNotifications 30 }


pBladeNonFatalHwErrorEvent NOTIFICATION-TYPE
    OBJECTS {
                pBladeIndex,
                pBladeFrameIndex,
                pBladeName,
                egeneraTrapSeverity,
                egeneraTrapMessage
            }
    STATUS      current
    DESCRIPTION
            "The notification generated when pBlade hardware detects a non-fatal
            error, such as a correctable ECC memory error.

            This trap is driven by 'pBlade <bladeframe>/p<1..24> NonFatal Hardware
            Error Event' event types.

            Severity: 3"

        ::=     { pBladeNotifications 31 }


pBladeFatalHwErrorEvent NOTIFICATION-TYPE
    OBJECTS {
                pBladeIndex,
                pBladeFrameIndex,
                pBladeName,
                egeneraTrapSeverity,
                egeneraTrapMessage
            }
    STATUS      current
    DESCRIPTION
            "The notification generated when pBlade hardware detects a fatal
            error, such as an uncorrectable ECC memory error.

            This trap is driven by 'pBlade <bladeframe>/p<1..24> Fatal Hardware
            Error Event' event types.

            Severity: 1"

        ::=     { pBladeNotifications 32 }


pBladeHwErrorThresholdEvent NOTIFICATION-TYPE
    OBJECTS {
                pBladeIndex,
                pBladeFrameIndex,
                pBladeName,
                egeneraTrapSeverity,
                egeneraTrapMessage
            }
    STATUS      current
    DESCRIPTION
            "The notification generated when pBlade is shutdown and marked
            out-of-service due to excessive fatal hardware errors

            This trap is driven by 'pBlade <bladeframe>/p<1..24> Hardware Error
            Threshold Event' event types

            Severity: 1"

        ::=     { pBladeNotifications 33 }


pBladeOutOfServicePendingEvent NOTIFICATION-TYPE
    OBJECTS {
                pBladeIndex,
                pBladeFrameIndex,
                pBladeName,
                egeneraTrapSeverity,
                egeneraTrapMessage
            }
    STATUS      current
    DESCRIPTION
            "The notification generated when a pBlade enters the 'out of service
            pending' state.

            This trap is driven by 'cBlade <bladeframe>/p<1..24> Out of Service Pending
            Event' event types

            Severity: 5"

        ::=     { pBladeNotifications 34 }


pBladeBootImageChangedEvent NOTIFICATION-TYPE
    OBJECTS {
                pBladeIndex,
                pBladeFrameIndex,
                pBladeName,
                egeneraTrapSeverity,
                egeneraTrapMessage
            }
    STATUS      current
    DESCRIPTION
            "The notification generated when a pBlade boot image is changed..

            This trap is driven by 'cBlade <bladeframe>/p<1..24> Boot Image Changed
            Event' event types

            Severity: 5"

        ::=     { pBladeNotifications 35 }


pBladeVbladeRamOvercommitEvent NOTIFICATION-TYPE
    OBJECTS {
                pBladeIndex,
                pBladeFrameIndex,
                pBladeName,
                egeneraTrapSeverity,
                egeneraTrapMessage
            }
    STATUS      current
    DESCRIPTION
            "The notification generated when vBlade RAM is overcommited on pBlade insert.

            This trap is driven by 'pBlade <bladeframe>/p<1..24> vBlade RAM Overcommit
            Event' event types

            Severity: 3"

        ::=     { pBladeNotifications 36 }



pBladeIpmiCeccThresholdEvent NOTIFICATION-TYPE
    OBJECTS {
                pBladeIndex,
                pBladeFrameIndex,
                pBladeName,
                egeneraTrapSeverity,
                egeneraTrapMessage
            }
    STATUS      current
    DESCRIPTION
            "The notification generated when a pBlade has met the Correctable ECC Event Threshold.

            This trap is driven by 'pBlade <bladeframe>/p<1..24> Ipmi Cecc Threshold
            Event' event types

            Severity: 2"

        ::=     { pBladeNotifications 37 }


pBladeWarmedEvent NOTIFICATION-TYPE
    OBJECTS {
                pBladeIndex,
                pBladeFrameIndex,
                pBladeName,
                egeneraTrapSeverity,
                egeneraTrapMessage
            }
    STATUS      current
    DESCRIPTION
            "The notification generated when a pBlade is set to the warm
             state.

             This trap is driven by 'pBlade <framename>/p<1..24> Warmed Event'
             event types.

             Severity: 5"

        ::=     { pBladeNotifications 38 }


pServerMigratingEvent NOTIFICATION-TYPE
    OBJECTS {
                pServerIndex,
                pServerLPanIndex,
                pServerName,
                lPanName,
                egeneraTrapSeverity,
                egeneraTrapMessage
            }
    STATUS      current
    DESCRIPTION
            "The notification generated when a pServer starts to migrate."

        ::=     { pServerNotifications 35 }

pServerMigratedEvent NOTIFICATION-TYPE
    OBJECTS {
                pServerIndex,
                pServerLPanIndex,
                pServerName,
                lPanName,
                egeneraTrapSeverity,
                egeneraTrapMessage
            }
    STATUS      current
    DESCRIPTION
            "The notification generated when a pServer migrate is succeeded."

        ::=     { pServerNotifications 36 }


pServerMigrateFailedEvent NOTIFICATION-TYPE
    OBJECTS {
                pServerIndex,
                pServerLPanIndex,
                pServerName,
                lPanName,
                egeneraTrapSeverity,
                egeneraTrapMessage
            }
    STATUS      current
    DESCRIPTION
            "The notification generated when a pServer fails to migrate."

        ::=     { pServerNotifications 37 }


pServerSuspendingEvent NOTIFICATION-TYPE
    OBJECTS {
                pServerIndex,
                pServerLPanIndex,
                pServerName,
                lPanName,
                egeneraTrapSeverity,
                egeneraTrapMessage
            }
    STATUS      current
    DESCRIPTION
            "The notification generated when a pServer starts to suspend."

        ::=     { pServerNotifications 38 }


pServerSuspendedEvent NOTIFICATION-TYPE
    OBJECTS {
                pServerIndex,
                pServerLPanIndex,
                pServerName,
                lPanName,
                egeneraTrapSeverity,
                egeneraTrapMessage
            }
    STATUS      current
    DESCRIPTION
            "The notification generated when a pServer supend is completed."

        ::=     { pServerNotifications 39 }


pServerSuspendFailedEvent NOTIFICATION-TYPE
    OBJECTS {
                pServerIndex,
                pServerLPanIndex,
                pServerName,
                lPanName,
                egeneraTrapSeverity,
                egeneraTrapMessage
            }
    STATUS      current
    DESCRIPTION
            "The notification generated when a pServer fails to suspend."

        ::=     { pServerNotifications 40 }


pServerResumingEvent NOTIFICATION-TYPE
    OBJECTS {
                pServerIndex,
                pServerLPanIndex,
                pServerName,
                lPanName,
                egeneraTrapSeverity,
                egeneraTrapMessage
            }
    STATUS      current
    DESCRIPTION
            "The notification generated when a pServer starts to resume."

        ::=     { pServerNotifications 41 }


pServerResumedEvent NOTIFICATION-TYPE
    OBJECTS {
                pServerIndex,
                pServerLPanIndex,
                pServerName,
                lPanName,
                egeneraTrapSeverity,
                egeneraTrapMessage
            }
    STATUS      current
    DESCRIPTION
            "The notification generated when a pServer resume is completed."

        ::=     { pServerNotifications 42 }


pServerResumeFailedEvent NOTIFICATION-TYPE
    OBJECTS {
                pServerIndex,
                pServerLPanIndex,
                pServerName,
                lPanName,
                egeneraTrapSeverity,
                egeneraTrapMessage
            }
    STATUS      current
    DESCRIPTION
            "The notification generated when a pServer fails to resume."

        ::=     { pServerNotifications 43 }

pServerUserMonitorFailedEvent NOTIFICATION-TYPE
    OBJECTS {
                pServerIndex,
                pServerLPanIndex,
                pServerName,
                lPanName,
                monitorName,
                ruleName,
                egeneraTrapSeverity,
                egeneraTrapMessage
            }
    STATUS      current
    DESCRIPTION
            "The notification generated when a user defined monitor is failed.

            This trap is driven by 'pServer <lpanname>/<pservername> User Monitor Failed Event:
            <lpanname>/<pservername>/<monitorname>

            Severity: 1"

        ::=     { pServerNotifications 44 }


lPanNotifications OBJECT IDENTIFIER ::= { egeneraNotifications 8 }


lPanCreatedEvent NOTIFICATION-TYPE
    OBJECTS {
                lPanIndex,
                lPanName,
                egeneraTrapSeverity,
                egeneraTrapMessage
            }
    STATUS      current
    DESCRIPTION
            "The notification generated when an LPAN is created.

            This trap is driven by 'LPAN <lpanname> create event' event types.

            Severity: 5"

        ::=     { lPanNotifications 1 }


lPanDeletedEvent NOTIFICATION-TYPE
    OBJECTS {
                lPanIndex,
                lPanName,
                egeneraTrapSeverity,
                egeneraTrapMessage
            }
    STATUS      current
    DESCRIPTION
            "The notification generated when an LPAN is deleted.

            This trap is driven by 'LPAN <lpanname> delete event' event types.

            Severity: 5"

        ::=     { lPanNotifications 2 }


lPanBootedEvent NOTIFICATION-TYPE
    OBJECTS {
                lPanIndex,
                lPanName,
                egeneraTrapSeverity,
                egeneraTrapMessage
            }
    STATUS      current
    DESCRIPTION
            "The notification generated when an LPAN is booted.

            This trap is driven by 'LPAN <lpanname> boot event' event types.

            Severity: 5"

        ::=     { lPanNotifications 3 }


lPanShutdownEvent NOTIFICATION-TYPE
    OBJECTS {
                lPanIndex,
                lPanName,
                egeneraTrapSeverity,
                egeneraTrapMessage
            }
    STATUS      current
    DESCRIPTION
            "The notification generated when an LPAN is shutdown.

            This trap is driven by 'LPAN <lpanname> shutdown event' event types.

            Severity: 5"

        ::=     { lPanNotifications 4 }


lPanResourceUnavailableEvent NOTIFICATION-TYPE
    OBJECTS {
                lPanIndex,
                lPanName,
                egeneraTrapSeverity,
                egeneraTrapMessage
            }
    STATUS      current
    DESCRIPTION
            "The notification generated when a resource required by the
            LPAN is unavailable.

            This trap is driven by 'LPAN <lpanname> resource unavailable event'
            event types.

            Severity: 3"

        ::=     { lPanNotifications 5 }


lPanModifyEvent NOTIFICATION-TYPE
    OBJECTS {
                lPanIndex,
                lPanName,
                egeneraTrapSeverity,
                egeneraTrapMessage
            }
    STATUS      current
    DESCRIPTION
            "The notification generated when when a logical PAN is
            modified.

            This trap is driven by 'LPAN <lpanname> Configuration Change
            Event' event types.

            Severity: 5"

        ::=     { lPanNotifications 6 }



lPanActivatedEvent NOTIFICATION-TYPE
    OBJECTS {
                lPanIndex,
                lPanName,
                egeneraTrapSeverity,
                egeneraTrapMessage
            }
    STATUS      current
    DESCRIPTION
            "The notification generated when when an LPAN is
            activated.

            This trap is driven by 'LPAN <lpanname> Activated Event'
            event types.

            Severity: 5"

        ::=     { lPanNotifications 7 }


lPanDeactivatedEvent NOTIFICATION-TYPE
    OBJECTS {
                lPanIndex,
                lPanName,
                egeneraTrapSeverity,
                egeneraTrapMessage
            }
    STATUS      current
    DESCRIPTION
            "The notification generated when when an LPAN is
            deactivated.

            This trap is driven by 'LPAN <lpanname> Deactivated Event'
            event types.

            Severity: 5"

        ::=     { lPanNotifications 8 }


lPanDeviceAvailableEvent NOTIFICATION-TYPE
    OBJECTS {
                lPanIndex,
                lPanName,
                egeneraTrapSeverity,
                egeneraTrapMessage
            }
    STATUS      current
    DESCRIPTION
            "The notification generated when when a device becomes available
            to an LPAN.

            This trap is driven by 'LPAN <lpanname> Device Available Event'
            event types.

            Severity: 5"

        ::=     { lPanNotifications 9 }


lPanDeviceUnavailableEvent NOTIFICATION-TYPE
    OBJECTS {
                lPanIndex,
                lPanName,
                egeneraTrapSeverity,
                egeneraTrapMessage
            }
    STATUS      current
    DESCRIPTION
            "The notification generated when when a device becomes unavailable
            to an LPAN.

            This trap is driven by 'LPAN <lpanname> Device Unavailable Event'
            event types.

            Severity: 5"

        ::=     { lPanNotifications 10 }


lPanPBladeAvailableEvent NOTIFICATION-TYPE
    OBJECTS {
                lPanIndex,
                lPanName,
                pBladeIndex,
                pBladeFrameIndex,
                pBladeName,
                egeneraTrapSeverity,
                egeneraTrapMessage
            }
    STATUS      current
    DESCRIPTION
            "The notification generated when when a pBlade becomes available
            to an LPAN.

            This trap is driven by 'LPAN <lpanname> pBlade Available Event'
            event types.

            Severity: 5"

        ::=     { lPanNotifications 11 }


lPanPBladeUnavailableEvent NOTIFICATION-TYPE
    OBJECTS {
                lPanIndex,
                lPanName,
                pBladeIndex,
                pBladeFrameIndex,
                pBladeName,
                egeneraTrapSeverity,
                egeneraTrapMessage
            }
    STATUS      current
    DESCRIPTION
            "The notification generated when when a pBlade becomes unavailable
            to an LPAN.

            This trap is driven by 'LPAN <lpanname> pBlade Unavailable Event'
            event types.

            Severity: 5"

        ::=     { lPanNotifications 12 }


lPanPBladeAllocatedEvent NOTIFICATION-TYPE
    OBJECTS {
                lPanIndex,
                lPanName,
                pBladeIndex,
                pBladeFrameIndex,
                pBladeName,
                egeneraTrapSeverity,
                egeneraTrapMessage
            }
    STATUS      current
    DESCRIPTION
            "The notification generated when when a pBlade is allocated
            to an LPAN.

            This trap is driven by 'pBlade <framename>/p<1..24> Allocated Event'
            event types.

            Severity: 5"

        ::=     { lPanNotifications 13 }


lPanPBladeDeallocatedEvent NOTIFICATION-TYPE
    OBJECTS {
                lPanIndex,
                lPanName,
                pBladeIndex,
                pBladeFrameIndex,
                pBladeName,
                egeneraTrapSeverity,
                egeneraTrapMessage
            }
    STATUS      current
    DESCRIPTION
            "The notification generated when when a pBlade is deallocated
            from an LPAN.

            This trap is driven by 'pBlade <framename>/p<1..24> Deallocated Event'
            event types.

            Severity: 5"

        ::=     { lPanNotifications 14 }


lPanUserMonitorCreatedEvent NOTIFICATION-TYPE
    OBJECTS {
                lPanIndex,
                lPanName,
                egeneraTrapSeverity,
                egeneraTrapMessage
            }
    STATUS      current
    DESCRIPTION
            "The notification generated when when a User Defined Monitor is created
            in an LPAN.

            This trap is driven by 'LPAN <lpanname> User Monitor Create Event'
            event types.

            Severity: 5"

        ::=     { lPanNotifications 15 }


lPanUserMonitorModifiedEvent NOTIFICATION-TYPE
    OBJECTS {
                lPanIndex,
                lPanName,
                egeneraTrapSeverity,
                egeneraTrapMessage
            }
    STATUS      current
    DESCRIPTION
            "The notification generated when when a User Defined Monitor is modified
            in an LPAN.

            This trap is driven by 'LPAN <lpanname> User Monitor Modified Event'
            event types.

            Severity: 5"

        ::=     { lPanNotifications 16 }


lPanUserMonitorDeletedEvent NOTIFICATION-TYPE
    OBJECTS {
                lPanIndex,
                lPanName,
                egeneraTrapSeverity,
                egeneraTrapMessage
            }
    STATUS      current
    DESCRIPTION
            "The notification generated when when a User Defined Monitor is deleted
            in an LPAN.

            This trap is driven by 'LPAN <lpanname> User Monitor Delete Event'
            event types.

            Severity: 5"

        ::=     { lPanNotifications 17 }


lPanOperationStartedEvent NOTIFICATION-TYPE
    OBJECTS {
                lPanIndex,
                lPanName,
                egeneraTrapSeverity,
                egeneraTrapMessage
            }
    STATUS      current
    DESCRIPTION
            "The notification generated when LPAN operation is initiated.

            This trap is driven by 'LPAN <lpanname> Operation Started Event'
            event types.

            Severity: 5"

        ::=     { lPanNotifications 18 }


lPanOperationCompletedEvent NOTIFICATION-TYPE
    OBJECTS {
                lPanIndex,
                lPanName,
                egeneraTrapSeverity,
                egeneraTrapMessage
            }
    STATUS      current
    DESCRIPTION
            "The notification generated when LPAN operation completes.

            This trap is driven by 'LPAN <lpanname> Operation Completed Event'
            event types.

            Severity: 5"

        ::=     { lPanNotifications 19 }


lPanOperationAbortedEvent NOTIFICATION-TYPE
    OBJECTS {
                lPanIndex,
                lPanName,
                egeneraTrapSeverity,
                egeneraTrapMessage
            }
    STATUS      current
    DESCRIPTION
            "The notification generated when LPAN operation is aborted.

            This trap is driven by 'LPAN <lpanname> Operation Aborted Event'
            event types.

            Severity: 5"

        ::=     { lPanNotifications 20 }


hypervisorGroupRecoverySetAddedEvent NOTIFICATION-TYPE
    OBJECTS {
                lPanIndex,
                lPanName,
                egeneraTrapSeverity,
                egeneraTrapMessage
            }
    STATUS      current
    DESCRIPTION
            "The notification is generated when a Hypervisor is added to a LPAN
	    Hypervisor Group Recovery set.

            This trap is driven by 'Hypervisor Added to Recovery Set for LPAN <lpanname> Hypervisor Group'
            event types.

            Severity: 5"

        ::=     { lPanNotifications 21 }


hypervisorGroupRecoverySetDeletedEvent NOTIFICATION-TYPE
    OBJECTS {
                lPanIndex,
                lPanName,
                egeneraTrapSeverity,
                egeneraTrapMessage
            }
    STATUS      current
    DESCRIPTION
            "The notification is generated when a Hypervisor is deleted
	    from Hypervisor Group recovery set.

            This trap is driven by 'Hypervisor Deleted from Recovery Set for LPAN <lpanname> Hypervisor Group'
            event types.

            Severity: 5"

        ::=     { lPanNotifications 22 }


hypervisorGroupAddedEvent NOTIFICATION-TYPE
    OBJECTS {
                lPanIndex,
                lPanName,
                egeneraTrapSeverity,
                egeneraTrapMessage
            }
    STATUS      current
    DESCRIPTION
            "The notification is generated when a Hypervisor is added to a LPAN Hypervisor Group.

            This trap is driven by 'Hypervisor Added to LPAN <lpanname> Hypervisor Group'
            event types.

            Severity: 5"

        ::=     { lPanNotifications 23 }


hypervisorGroupDeletedEvent NOTIFICATION-TYPE
    OBJECTS {
                lPanIndex,
                lPanName,
                egeneraTrapSeverity,
                egeneraTrapMessage
            }
    STATUS      current
    DESCRIPTION
            "The notification is generated when a Hypervisor is deleted from a LPAN Hypervisor Group.

            This trap is driven by 'Hypervisor Deleted from LPAN <lpanname> Hypervisor Group'
            event types.

            Severity: 5"

        ::=     { lPanNotifications 24 }


hypervisorGroupRecoveryModeEnteredEvent NOTIFICATION-TYPE
    OBJECTS {
                lPanIndex,
                lPanName,
                egeneraTrapSeverity,
                egeneraTrapMessage
            }
    STATUS      current
    DESCRIPTION
            "The notification generated when a LPAN Hypervisor Group enters manual recovery
	    mode following auto-recovery failure.

            This trap is driven by 'LPAN <lpanname> Entered Manual Recovery Mode'
            event types.

            Severity: 1"

        ::=     { lPanNotifications 25 }


hypervisorGroupRecoveryModeDepartedEvent NOTIFICATION-TYPE
    OBJECTS {
                lPanIndex,
                lPanName,
                egeneraTrapSeverity,
                egeneraTrapMessage
            }
    STATUS      current
    DESCRIPTION
            "The notification generated when a LPAN Hypervisor Group is no
	    longer in manual recovery mode.

            This trap is driven by 'LPAN <lpanname> Departs Manual Recovery Mode'
            event types.

            Severity: 5"

        ::=     { lPanNotifications 26 }


hypervisorBootFailedEvent NOTIFICATION-TYPE
    OBJECTS {
                lPanIndex,
                lPanName,
                egeneraTrapSeverity,
                egeneraTrapMessage
            }
    STATUS      current
    DESCRIPTION
            "The notification generated when a Hypervisor boot is explicitly failed
	    for various reasons including that the LPAN Hypervisor Group is in recovery.

            This trap is driven by 'LPAN <lpanname> Hypervisor Boot Failed'
            event types.

            Severity:3 "

        ::=     { lPanNotifications 27 }


hypervisorGroupMasterAssignedEvent NOTIFICATION-TYPE
    OBJECTS {
                lPanIndex,
                lPanName,
                egeneraTrapSeverity,
                egeneraTrapMessage
            }
    STATUS      current
    DESCRIPTION
            "The notification generated when a Hypervisor is assigned as Master
	    of a LPAN Hypervisor Group.

            This trap is driven by 'LPAN <lpanname> Hypervisor Group Master Assigned'
            event types.

            Severity: 5"

        ::=     { lPanNotifications 28 }


hypervisorGroupMasterAssignFailedEvent NOTIFICATION-TYPE
    OBJECTS {
                lPanIndex,
                lPanName,
                egeneraTrapSeverity,
                egeneraTrapMessage
            }
    STATUS      current
    DESCRIPTION
            "The notification generated when assignment of a Hypervisor as Master fails.

            This trap is driven by 'LPAN <lpanname> Hypervisor Group Master Assignment Failed'
            event types.

            Severity: 2"

        ::=     { lPanNotifications 29 }


hypervisorGroupSlaveAssignedEvent NOTIFICATION-TYPE
    OBJECTS {
                lPanIndex,
                lPanName,
                egeneraTrapSeverity,
                egeneraTrapMessage
            }
    STATUS      current
    DESCRIPTION
            "The notification generated when a Hypervisor is assigned as Slave
	    of a LPAN Hypervisor Group.

            This trap is driven by 'LPAN <lpanname> Hypervisor Group Slave Assigned'
            event types.

            Severity: 5"

        ::=     { lPanNotifications 30 }


hypervisorGroupSlaveAssignFailedEvent NOTIFICATION-TYPE
    OBJECTS {
                lPanIndex,
                lPanName,
                egeneraTrapSeverity,
                egeneraTrapMessage
            }
    STATUS      current
    DESCRIPTION
            "The notification generated when assignment of a Hypervisor as Slave fails.

            This trap is driven by 'LPAN <lpanname> Hypervisor Group Slave Assignment Failed'
            event types.

            Severity: 2"

        ::=     { lPanNotifications 31 }


hypervisorGroupMasterClearedEvent NOTIFICATION-TYPE
    OBJECTS {
                lPanIndex,
                lPanName,
                egeneraTrapSeverity,
                egeneraTrapMessage
            }
    STATUS      current
    DESCRIPTION
            "The notification generated when a Hypervisor is cleared as Master
	    of a LPAN Hypervisor Group.

            This trap is driven by 'LPAN <lpanname> Hypervisor Group Master Cleared'
            event types.

            Severity: 5"

        ::=     { lPanNotifications 32 }


hypervisorGroupSlaveClearedEvent NOTIFICATION-TYPE
    OBJECTS {
                lPanIndex,
                lPanName,
                egeneraTrapSeverity,
                egeneraTrapMessage
            }
    STATUS      current
    DESCRIPTION
            "The notification generated when a Hypervisor is cleared as Slave
	    of a LPAN Hypervisor Group.

            This trap is driven by 'LPAN <lpanname> Hypervisor Group Slave Cleared'
            event types.

            Severity: 5"

        ::=     { lPanNotifications 33 }


hypervisorGroupSlaveNotifiedEvent NOTIFICATION-TYPE
    OBJECTS {
                lPanIndex,
                lPanName,
                egeneraTrapSeverity,
                egeneraTrapMessage
            }
    STATUS      current
    DESCRIPTION
            "The notification generated when a Slave Hypervisor is notified of a new Master.

            This trap is driven by 'LPAN <lpanname> Hypervisor Group Slave Notified of New Master'
            event types.

            Severity: 5"

        ::=     { lPanNotifications 34 }


hypervisorGroupSlaveNotificationFailedEvent NOTIFICATION-TYPE
    OBJECTS {
                lPanIndex,
                lPanName,
                egeneraTrapSeverity,
                egeneraTrapMessage
            }
    STATUS      current
    DESCRIPTION
            "The notification generated when a Slave Hypervisor notificiation of a new Master fails.

            This trap is driven by 'LPAN <lpanname> Hypervisor Group Slave New Master Notification Failed'
            event types.

            Severity: 2"

        ::=     { lPanNotifications 35 }


hypervisorGroupSlavePurgedEvent NOTIFICATION-TYPE
    OBJECTS {
                lPanIndex,
                lPanName,
                egeneraTrapSeverity,
                egeneraTrapMessage
            }
    STATUS      current
    DESCRIPTION
            "The notification generated when a Master Hypervisor is purged of a Slave Hypervisor.

            This trap is driven by 'LPAN <lpanname> Hypervisor Group Master Purged of Slave Hypervisor'
            event types.

            Severity: 5"

        ::=     { lPanNotifications 36 }
 

hypervisorGroupSlavePurgeFailedEvent NOTIFICATION-TYPE
    OBJECTS {
                lPanIndex,
                lPanName,
                egeneraTrapSeverity,
                egeneraTrapMessage
            }
    STATUS      current
    DESCRIPTION
            "The notification generated when Master purge of Slave hypervisor fails.

            This trap is driven by 'LPAN <lpanname> Hypervisor Group Master Purge of Slave Hypervisor Failed'
            event types.

            Severity: 2"

        ::=     { lPanNotifications 37 }


pServerNotifications OBJECT IDENTIFIER ::= { egeneraNotifications 9 }

pServerBootedEvent NOTIFICATION-TYPE
    OBJECTS {
                pServerIndex,
                pServerLPanIndex,
                pServerName,
                lPanName,
                egeneraTrapSeverity,
                egeneraTrapMessage
            }
    STATUS      current
    DESCRIPTION
            "The notification generated when a pServer is booted.

            This trap is driven by 'pServer <lpanname>/<pservername> boot
            event' event types.

            Severity: 5"

        ::=     { pServerNotifications 1 }


pServerShutdownEvent NOTIFICATION-TYPE
    OBJECTS {
                pServerIndex,
                pServerLPanIndex,
                pServerName,
                lPanName,
                egeneraTrapSeverity,
                egeneraTrapMessage
            }
    STATUS      current
    DESCRIPTION
            "The notification generated when a pServer is shutdown.

            This trap is driven by 'pServer <lpanname>/<pservername> shutdown
            event' event types.

            Severity: 5"

        ::=     { pServerNotifications 2 }


pServerBootFailedEvent NOTIFICATION-TYPE
    OBJECTS {
                pServerIndex,
                pServerLPanIndex,
                pServerName,
                lPanName,
                egeneraTrapSeverity,
                egeneraTrapMessage
            }
    STATUS      current
    DESCRIPTION
            "The notification generated when a pServer fails to boot.

            This trap is driven by 'pServer <lpanname>/<pservername> Boot Failed
            Event' event types.

            Severity: 2"

        ::=     { pServerNotifications 3 }


pServerDebuggerEnterEvent NOTIFICATION-TYPE
    OBJECTS {
                pServerIndex,
                pServerLPanIndex,
                pServerName,
                lPanName,
                egeneraTrapSeverity,
                egeneraTrapMessage
            }
    STATUS      current
    DESCRIPTION
            "The notification generated when the debbugger has been invoked
            on the pServer.

            This trap is driven by 'blade.status.monitor.event' event types
            that describe a pBlade transition to the 'in kdb' state.

            This event type is not user visible, and will not appear in
            CLI or GUI event queries.  The trap exists to satisfy early
            requirements documents.

            Severity: 3"

        ::=     { pServerNotifications 5 }


pServerDebuggerExitEvent NOTIFICATION-TYPE
    OBJECTS {
                pServerIndex,
                pServerLPanIndex,
                pServerName,
                lPanName,
                egeneraTrapSeverity,
                egeneraTrapMessage
            }
    STATUS      current
    DESCRIPTION
            "The notification generated when the debbugger has been exited
            on the pServer.

            This trap is driven by 'blade.status.monitor.event' event types
            that describe a pBlade transition from the 'in kdb' state.

            This event type is not user visible, and will not appear in
            CLI or GUI event queries.  The trap exists to satisfy early
            requirements documents.

            Severity: 3"

        ::=     { pServerNotifications 6 }


pServerResourceUnavailableEvent NOTIFICATION-TYPE
    OBJECTS {
                pServerIndex,
                pServerLPanIndex,
                pServerName,
                lPanName,
                egeneraTrapSeverity,
                egeneraTrapMessage
            }
    STATUS      current
    DESCRIPTION
            "This trap is deprecated as of PAN Manager release 4.0."

        ::=     { pServerNotifications 7 }


pServerSystemThresholdHighEvent NOTIFICATION-TYPE
    OBJECTS {
                pServerIndex,
                pServerLPanIndex,
                pServerName,
                lPanName,
                egeneraTrapSeverity,
                egeneraTrapMessage
            }
    STATUS      current
    DESCRIPTION
            "The notification generated when a pServer system monitor has
            exceeded its high threshold, returns below the high threshold.

            This trap is driven by 'pServer <lpanname>/<pservername> <monitorname>
            event' event types.  Note that a severity 3 event is emmitted when
            the threshold is crossed in the rising direction, while a severity
            5 event is emmitted when the monitored value returns below the threshold.
            Thus it is possible to recieve a severity 5 pServerSystemThresholdHighTrap
            with a message like:

            pcw/p2 pServer pcw/p2 5 Minute Load Average returned below 10.0 on average
            for 300 seconds, Current value = 4.79

            Severity: 3/5"

        ::=     { pServerNotifications 8 }


pServerSystemThresholdlowEvent NOTIFICATION-TYPE
    OBJECTS {
                pServerIndex,
                pServerLPanIndex,
                pServerName,
                lPanName,
                egeneraTrapSeverity,
                egeneraTrapMessage
            }
    STATUS      current
    DESCRIPTION
            "The notification generated when a pServer system monitor has
            exceeded its low threshold, or returns above the low threshold.

            Currently, no software values are monitored for critically low
            values, and this trap is not emitted.  Because there is no
            driving event type, there is no severity."

        ::=     { pServerNotifications 9 }


pServerFailedEvent NOTIFICATION-TYPE
    OBJECTS {
                pServerIndex,
                pServerLPanIndex,
                pServerName,
                lPanName,
                egeneraTrapSeverity,
                egeneraTrapMessage
            }
    STATUS      current
    DESCRIPTION
            "The notification generated when a booted pServer fails.

            This trap is driven by 'pServer <lpanname>/<pservername> failed
            event' event types.

            Severity: 2"

        ::=     { pServerNotifications 10 }


pServerRecoverEvent NOTIFICATION-TYPE
    OBJECTS {
                pServerIndex,
                pServerLPanIndex,
                pServerName,
                lPanName,
                egeneraTrapSeverity,
                egeneraTrapMessage
            }
    STATUS      current
    DESCRIPTION
            "The notification generated when a failed pServer has been
            successfully recovered, generally due to pBlade failover.

            This trap is driven by 'pServer <lpanname>/<pservername> recover
            event' event types.

            Severity: 5"

        ::=     { pServerNotifications 11 }


pServerBootingEvent NOTIFICATION-TYPE
    OBJECTS {
                pServerIndex,
                pServerLPanIndex,
                pServerName,
                lPanName,
                egeneraTrapSeverity,
                egeneraTrapMessage
            }
    STATUS      current
    DESCRIPTION
            "The notification generated when a pServer begins the process
            of booting.

            This trap is driven by 'pServer <lpanname>/<pservername> Booting
            Event' event types.

            Severity: 5"

        ::=     { pServerNotifications 12 }


pServerCreatedEvent NOTIFICATION-TYPE
    OBJECTS {
                pServerIndex,
                pServerLPanIndex,
                pServerName,
                lPanName,
                egeneraTrapSeverity,
                egeneraTrapMessage
            }
    STATUS      current
    DESCRIPTION
            "The notification generated when a pServer is created.

            This trap is driven by 'pServer <lpanname>/<pservername> create
            event' event types.

            Severity: 5"

        ::=     { pServerNotifications 13 }


pServerDeletedEvent NOTIFICATION-TYPE
    OBJECTS {
                pServerIndex,
                pServerLPanIndex,
                pServerName,
                lPanName,
                egeneraTrapSeverity,
                egeneraTrapMessage
            }
    STATUS      current
    DESCRIPTION
            "The notification generated when a pServer is deleted.

            This trap is driven by 'pServer <lpanname>/<pservername> delete
            event' event types.

            Severity: 5"

        ::=     { pServerNotifications 14 }


pServerFailoverEvent NOTIFICATION-TYPE
    OBJECTS {
                pServerIndex,
                pServerLPanIndex,
                pServerName,
                lPanName,
                egeneraTrapSeverity,
                egeneraTrapMessage
            }
    STATUS      current
    DESCRIPTION
            "The notification generated when a pServer begins the process
            of failing over.

            This trap is driven by 'pServer <lpanname>/<pservername> Failover
            attempted Event' event types.

            Severity: 3"

        ::=     { pServerNotifications 15 }


pServerModifiedEvent NOTIFICATION-TYPE
    OBJECTS {
                pServerIndex,
                pServerLPanIndex,
                pServerName,
                lPanName,
                egeneraTrapSeverity,
                egeneraTrapMessage
            }
    STATUS      current
    DESCRIPTION
           "The notification generated when a pServer configuration is
           modified.

           This trap is driven by 'pServer <lpanname>/<pservername> Configuration
           Change Event' event types.

           Severity: 5"

        ::=     { pServerNotifications 16 }


pServerRebootingEvent NOTIFICATION-TYPE
    OBJECTS {
                pServerIndex,
                pServerLPanIndex,
                pServerName,
                lPanName,
                egeneraTrapSeverity,
                egeneraTrapMessage
            }
    STATUS      current
    DESCRIPTION
            "The notification generated when a pServer reboot has initiated.

            This trap is driven by 'pServer <lpanname>/<pservername> Rebooting
            Event' event types.

            Severity: 5"

        ::=     { pServerNotifications 17 }


pServerShuttingDownEvent NOTIFICATION-TYPE
    OBJECTS {
                pServerIndex,
                pServerLPanIndex,
                pServerName,
                lPanName,
                egeneraTrapSeverity,
                egeneraTrapMessage
            }
    STATUS      current
    DESCRIPTION
            "The notification generated when a pServer shutdown has initiated.

            This trap is driven by 'pServer <lpanname>/<pservername> Shutting
            Down Event' event types.

            Severity: 5"

        ::=     { pServerNotifications 18 }


pServerAgentArrivedEvent NOTIFICATION-TYPE
    OBJECTS {
                pServerIndex,
                pServerLPanIndex,
                pServerName,
                lPanName,
                egeneraTrapSeverity,
                egeneraTrapMessage
            }
    STATUS      current
    DESCRIPTION
            "The notification generated when a pServer agent has arrived.

            This trap is driven by 'pServer <lpanname>/<pservername> Agent
            Available Event' event types

            Severity: 5"

        ::=     { pServerNotifications 19 }


pServerAgentDepartedEvent NOTIFICATION-TYPE
    OBJECTS {
                pServerIndex,
                pServerLPanIndex,
                pServerName,
                lPanName,
                egeneraTrapSeverity,
                egeneraTrapMessage
            }
    STATUS      current
    DESCRIPTION
            "The notification generated when a pServer agent has departed.

            This trap is driven by  'pServer <lpanname>/<pservername> PAN
            Agent Unavailable Event' event types.

            Severity: 5"

        ::=     { pServerNotifications 20 }


pServerAgentGetDataFailedEvent NOTIFICATION-TYPE
    OBJECTS {
                pServerIndex,
                pServerLPanIndex,
                pServerName,
                lPanName,
                egeneraTrapSeverity,
                egeneraTrapMessage
            }
    STATUS      current
    DESCRIPTION
            "The notification generated when a pServer agent does not return
            requests for statistical data.

            This trap is driven by  'pServer <lpanname>/<pservername> PAN
            Agent ' event types.

            Severity: 3"

        ::=     { pServerNotifications 47 }


pServerHardwareOnlineEvent NOTIFICATION-TYPE
    OBJECTS {
                pServerIndex,
                pServerLPanIndex,
                pServerName,
                lPanName,
                egeneraTrapSeverity,
                egeneraTrapMessage
            }
    STATUS      current
    DESCRIPTION
            "The notification generated when hardware for a pServer agent
            goes online.

            This trap is driven by  'pServer <lpanname>/<pservername> Hardware
            Online Event' event types.

            Severity: 5"

        ::=     { pServerNotifications 28 }


pServerHardwareOfflineEvent NOTIFICATION-TYPE
    OBJECTS {
                pServerIndex,
                pServerLPanIndex,
                pServerName,
                lPanName,
                egeneraTrapSeverity,
                egeneraTrapMessage
            }
    STATUS      current
    DESCRIPTION
            "The notification generated when hardware for a pServer agent
            goes offline.

            This trap is driven by  'pServer <lpanname>/<pservername> Hardware
            Offline Event' event types.

            Severity: 5"

        ::=     { pServerNotifications 29 }


pServerRecoveredEvent NOTIFICATION-TYPE
    OBJECTS {
                pServerIndex,
                pServerLPanIndex,
                pServerName,
                lPanName,
                egeneraTrapSeverity,
                egeneraTrapMessage
            }
    STATUS      current
    DESCRIPTION
            "The notification generated when pServer recovers from a failure.

            This trap is driven by  'pServer <lpanname>/<pservername> Recovered
            Event' event types.

            Severity: 5"

        ::=     { pServerNotifications 30 }


pServerDiskAvailableEvent NOTIFICATION-TYPE
    OBJECTS {
                pServerIndex,
                pServerLPanIndex,
                pServerName,
                lPanName,
                diskIdOctets,
                egeneraTrapSeverity,
                egeneraTrapMessage
            }
    STATUS      current
    DESCRIPTION
            "The notification generated when a disk on a pServer becomes available.

            This trap is driven by  'pServer <lpanname>/<pservername> Disk
            Available Event' event types.

            Severity: 5"

        ::=     { pServerNotifications 31 }


pServerDiskUnavailableEvent NOTIFICATION-TYPE
    OBJECTS {
                pServerIndex,
                pServerLPanIndex,
                pServerName,
                lPanName,
                diskIdOctets,
                egeneraTrapSeverity,
                egeneraTrapMessage
            }
    STATUS      current
    DESCRIPTION
            "The notification generated when a disk on a pServer is unavailable
            at boot time.

            This trap is driven by  'pServer <lpanname>/<pservername> Disk
            Unavailable Event' event types.

            Severity: 3"

        ::=     { pServerNotifications 32 }


pServerOperationStartedEvent NOTIFICATION-TYPE
    OBJECTS {
                pServerIndex,
                pServerLPanIndex,
                pServerName,
                lPanName,
                egeneraTrapSeverity,
                egeneraTrapMessage
            }
    STATUS      current
    DESCRIPTION
            "The notification generated when a pServer operation has been
            invoked.

            This trap is driven by  'pServer <lpanname>/<pservername> Operation
            Started' event types.

            Severity: 5"

        ::=     { pServerNotifications 33 }


pServerPBladeAvailableEvent NOTIFICATION-TYPE
    OBJECTS {
                pServerIndex,
                pServerLPanIndex,
                pServerName,
                lPanName,
                egeneraTrapSeverity,
                egeneraTrapMessage
            }
    STATUS      current
    DESCRIPTION
            "The notification generated when a pServer pBlade becomes available.

            This trap is driven by  'pServer <lpanname>/<pservername> pBlade
            Available Event' event types.

            Severity: 5"

        ::=     { pServerNotifications 34 }


-- The PAN Manager provides functionality to monitor messages from syslogd.
-- When properly configured and enabled, EES defines a set of strings to
-- search syslog messages for.  When encountered, these syslog messages are
-- promoted to Egenera PAN Manager events.  The search strings and event
-- severities are defined by EES.  There are 10 event types reserved for
-- cBlade syslog messages, and 10 event types reserved for pServer syslog
-- messages.  Contact EES for more information.

pServerSyslogEvent NOTIFICATION-TYPE
    OBJECTS {
                pServerIndex,
                pServerLPanIndex,
                pServerName,
                lPanName,
                egeneraTrapSeverity,
                egeneraTrapMessage
            }
    STATUS      current
    DESCRIPTION
            "The notification sent when a syslog target string is emmited
            from the system logger.

            This trap is driven by 'pServer <lpanname>/<pservername> Custom
            Linux System Message <1..10>' event types.  See 'eventtype -l' for
            more information.

            There are 10 pServer syslog event types.  This trap can be
            enabled/disabled for each syslog event type independently.

            Severity: (configurable by EES, generally 1, 2 or 3)"

        ::=     { pServerNotifications 4 }


pServerSyslogDroppedEvent NOTIFICATION-TYPE
    OBJECTS {
                pServerIndex,
                pServerLPanIndex,
                pServerName,
                lPanName,
                egeneraTrapSeverity,
                egeneraTrapMessage
            }
    STATUS      current
    DESCRIPTION
            "The notification sent when a syslog target string message
            is dropped due to rate limiting.

            This trap is driven by 'pServer <lpanname>/<pservername> Custom Linux
            System Messages dropped' event types.  System message events are
            subject to rate limiting.  By default, no more than 5 messages can be
            emitted during a 5 minute period.  If more than 5 target strings are
            encountered, events will only be created for the first 5 messages,
            subsequent messages will be dropped.  At the end of the 5 minute
            period, a 'Messages Dropped' event will be emmitted to indicate
            the number of dropped messages during the 5 minute period.
            Contact EES for more information.

            Severity: 3"

        ::=     { pServerNotifications 21 }


pServerSyslogPollingStoppedEvent NOTIFICATION-TYPE
    OBJECTS {
                pServerIndex,
                pServerLPanIndex,
                pServerName,
                lPanName,
                egeneraTrapSeverity,
                egeneraTrapMessage
            }
    STATUS      current
    DESCRIPTION
            "The notification sent when a syslog polling has stopped
            due to rate limiting.

            This trap is driven by the 'pServer <lpanname>/<pservername> Custom
            Linux System Messages polling stopped' event type.  System message
            events are subject to rate limiting.  By default, no more than 5
            messages can be emitted during a 5 minute period.  If more than 5
            target strings are encountered, events will only be created for the
            first 5 messages, subsequent messages will be dropped.  If messages
            are dropped for 5 consecutive 5 minute periods, syslog message
            polling will be disabled on that cBlade.  Contact EES for more
            information.

            Severity: 2"

        ::=     { pServerNotifications 22 }


pServerShutdownFailedEvent NOTIFICATION-TYPE
    OBJECTS {
                pServerIndex,
                pServerLPanIndex,
                pServerName,
                lPanName,
                egeneraTrapSeverity,
                egeneraTrapMessage
            }
    STATUS      current
    DESCRIPTION
            "The notification sent when a pServer shutdown fails.

            This trap is driven by the 'pServer <lpanname>/<pservername>
            Shutdown Failed Event' event type.

            Severity: 3"

        ::=     { pServerNotifications 23 }


pServerPBladeAllocatedEvent NOTIFICATION-TYPE
    OBJECTS {
                pServerIndex,
                pServerLPanIndex,
                pServerName,
                lPanName,
                pBladeIndex,
                pBladeFrameIndex,
                pBladeName,
                egeneraTrapSeverity,
                egeneraTrapMessage
            }
    STATUS      current
    DESCRIPTION
            "The notification generated when when a pBlade is allocated
            to a pServer.

            This trap is driven by 'pBlade <framename>/p<1..24> Allocated Event'
            event types.

            Severity: 5"

        ::=     { pServerNotifications 24 }


pServerPBladeDeallocatedEvent NOTIFICATION-TYPE
    OBJECTS {
                pServerIndex,
                pServerLPanIndex,
                pServerName,
                lPanName,
                pBladeIndex,
                pBladeFrameIndex,
                pBladeName,
                egeneraTrapSeverity,
                egeneraTrapMessage
            }
    STATUS      current
    DESCRIPTION
            "The notification generated when when a pBlade is deallocated
            from a pServer.

            This trap is driven by 'pBlade <framename>/p<1..24> Deallocated Event'
            event types.

            Severity: 5"

        ::=     { pServerNotifications 25 }


pServerPanicCycleEvent NOTIFICATION-TYPE
    OBJECTS {
                pServerIndex,
                pServerLPanIndex,
                pServerName,
                lPanName,
                egeneraTrapSeverity,
                egeneraTrapMessage
            }
    STATUS      current
    DESCRIPTION
            "The notification generated when when a pServer panic cycle
            is detected.

            This trap is driven by 'pServer <framename>/p<1..24> Panic Cycle
            Event'

            Severity: 2"

        ::=     { pServerNotifications 26 }


pServerUserMonitorEvent NOTIFICATION-TYPE
    OBJECTS {
                pServerIndex,
                pServerLPanIndex,
                pServerName,
                lPanName,
                monitorName,
                ruleName,
                egeneraTrapSeverity,
                egeneraTrapMessage
            }
    STATUS      current
    DESCRIPTION
            "The notification generated when a user defined monitor rule is matched.

            This trap is driven by 'pServer <lpanname>/<pservername> User Monitor Event:
            <lpanname>/<pservername>/<monitorname>

            Severity: 1"

        ::=     { pServerNotifications 27 }

 pServerVBladeAllocatedEvent NOTIFICATION-TYPE
     OBJECTS {
                 pServerIndex,
                 pServerLPanIndex,
                 pServerName,
                 lPanName,
                 vBladeIndex,
                 vBladePBladeIndex,
                 vBladeFrameIndex,
                 vBladeName,
                 egeneraTrapSeverity,
                 egeneraTrapMessage
             }
     STATUS      current
     DESCRIPTION
             "The notification generated when when a vBlade is allocated
             to a pServer.

             This trap is driven by 'vBlade <framename>/p<1..24-1..n> Allocated Event'
             event types.

             Severity: 5"

         ::=     { pServerNotifications 45 }

 pServerVBladeDeallocatedEvent NOTIFICATION-TYPE
     OBJECTS {
                 pServerIndex,
                 pServerLPanIndex,
                 pServerName,
                 lPanName,
                 vBladeIndex,
                 vBladePBladeIndex,
                 vBladeFrameIndex,
                 vBladeName,
                 egeneraTrapSeverity,
                 egeneraTrapMessage
             }
     STATUS      current
     DESCRIPTION
             "The notification generated when when a pBlade is deallocated
             from a pServer.

             This trap is driven by 'vBlade <framename>/p<1..24-1..n> Deallocated Event'
             event types.

             Severity: 5"

         ::=     { pServerNotifications 46 }



failoverPoolNotifications OBJECT IDENTIFIER ::= { egeneraNotifications 10 }

failoverPoolExaustedEvent NOTIFICATION-TYPE
    OBJECTS {
                bladeFrameIndex,
                bladeFrameName,
                egeneraTrapSeverity,
                egeneraTrapMessage
            }
    STATUS      current
    DESCRIPTION
            "The notification generated when a failover blade pool is
            exhausted.

            This trap is deprecated because there is no underlying event
            to drive the trap.  The trap definition exists to satisfy early
            requirements documents."

        ::=     { failoverPoolNotifications 1 }


applicationNotifications OBJECT IDENTIFIER ::= { egeneraNotifications 11 }

-- application traps are grouped by logical order.
-- the lexicographical ordering does not group associated
-- traps together due to deprecation of previous traps
-- and inclusion of new traps

-- app create/modify/delete
applicationCreatedEvent NOTIFICATION-TYPE
    OBJECTS {
                applicationIndex,
                applicationLPanIndex,
                applicationName,
                egeneraTrapSeverity,
                egeneraTrapMessage
            }
    STATUS      current
    DESCRIPTION
            "The notification generated when an application has been
            created.

            This trap is driven by 'LPAN <lpanname> application Create
            Event' event types.

            Severity: 5"

        ::=     { applicationNotifications 17 }


applicationModifyEvent NOTIFICATION-TYPE
    OBJECTS {
                applicationIndex,
                applicationLPanIndex,
                applicationName,
                egeneraTrapSeverity,
                egeneraTrapMessage
            }
    STATUS      current
    DESCRIPTION
            "The notification generated when an application is modified.

            This trap is driven by 'application <lpanname>/<appname> Changed
            Event' event types.

            Severity: 5"

        ::=     { applicationNotifications 18 }


applicationDeletedEvent NOTIFICATION-TYPE
    OBJECTS {
                applicationIndex,
                applicationLPanIndex,
                applicationName,
                egeneraTrapSeverity,
                egeneraTrapMessage
            }
    STATUS      current
    DESCRIPTION
            "The notification generated when an application has been
            deleted.

            This trap is driven by 'LPAN <lpanname> application Delete
            Event' event types.

            Severity: 5"

        ::=     { applicationNotifications 19 }


-- app starting/started/start failed
applicationStartingEvent NOTIFICATION-TYPE
    OBJECTS {
                applicationIndex,
                applicationLPanIndex,
                applicationName,
                egeneraTrapSeverity,
                egeneraTrapMessage
            }
    STATUS      current
    DESCRIPTION
            "The notification generated when an application start has been
            initiated.

            This trap is driven by 'application <lpanname>/<appname> Start
            Started Event' event types.

            Severity: 5"

        ::=     { applicationNotifications 20 }



applicationStartedEvent NOTIFICATION-TYPE
    OBJECTS {
                applicationIndex,
                applicationLPanIndex,
                applicationName,
                egeneraTrapSeverity,
                egeneraTrapMessage
            }
    STATUS      current
    DESCRIPTION
            "The notification generated when an application has started
            successfully.

            This trap is driven by 'application <lpanname>/<appname> Start Completed
            Event ' event types.

            Severity: 5"

        ::=     { applicationNotifications 1 }


applicationStartFailedEvent NOTIFICATION-TYPE
    OBJECTS {
                applicationIndex,
                applicationLPanIndex,
                applicationName,
                egeneraTrapSeverity,
                egeneraTrapMessage
            }
    STATUS      current
    DESCRIPTION
            "The notification generated when an application start attempt
            has failed.

            This trap is driven by 'application <lpanname>/<appname> Start Failed
            Event' event types.

            Severity: 2"

        ::=     { applicationNotifications 21 }

-- app stopping/stopped/stop failed
applicationStoppingEvent NOTIFICATION-TYPE
    OBJECTS {
                applicationIndex,
                applicationLPanIndex,
                applicationName,
                egeneraTrapSeverity,
                egeneraTrapMessage
            }
    STATUS      current
    DESCRIPTION
            "The notification generated when an application stop has been
            initiated.

            This trap is driven by 'application <lpanname>/<appname> Stop
            Started Event' event types.

            Severity: 5"

        ::=     { applicationNotifications 22 }


applicationStoppedEvent NOTIFICATION-TYPE
    OBJECTS {
                applicationIndex,
                applicationLPanIndex,
                applicationName,
                egeneraTrapSeverity,
                egeneraTrapMessage
            }
    STATUS      current
    DESCRIPTION
            "The notification generated when an application has been
            successfully stopped.

            This trap is driven by 'application <lpanname>/<appname> Stop
            Completed Event' event types.

            Severity: 5"

        ::=     { applicationNotifications 2 }


applicationStopFailedEvent NOTIFICATION-TYPE
    OBJECTS {
                applicationIndex,
                applicationLPanIndex,
                applicationName,
                egeneraTrapSeverity,
                egeneraTrapMessage
            }
    STATUS      current
    DESCRIPTION
            "The notification generated when an application has failed
            to stop.

            This trap is driven by 'application <lpanname>/<appname> Stop
            Failed Event' event types.

            Severity: 2"

        ::=     { applicationNotifications 23 }


-- app moving/moved/move failed
applicationMovingEvent NOTIFICATION-TYPE
    OBJECTS {
                applicationIndex,
                applicationLPanIndex,
                applicationName,
                egeneraTrapSeverity,
                egeneraTrapMessage
            }
    STATUS      current
    DESCRIPTION
            "The notification generated when an application move
            has been initiated.

            This trap is driven by 'application <lpanname>/<appname> Move
            Started Event' event types.

            Severity: 5"

        ::=     { applicationNotifications 24 }


applicationMovedEvent NOTIFICATION-TYPE
    OBJECTS {
                applicationIndex,
                applicationLPanIndex,
                applicationName,
                egeneraTrapSeverity,
                egeneraTrapMessage
            }
    STATUS      current
    DESCRIPTION
            "The notification generated when an application move
            has successfully completed.

            This trap is driven by 'application <lpanname>/<appname> Move
            Completed Event' event types.

            Severity: 5"

        ::=     { applicationNotifications 25 }


applicationMoveFailedEvent NOTIFICATION-TYPE
    OBJECTS {
                applicationIndex,
                applicationLPanIndex,
                applicationName,
                egeneraTrapSeverity,
                egeneraTrapMessage
            }
    STATUS      current
    DESCRIPTION
            "The notification generated when an application move
            has failed.

            This trap is driven by 'application <lpanname>/<appname> Move
            Failed Event' event types.

            Severity: 5"

        ::=     { applicationNotifications 26 }


-- app failing over/failed over/failover failed
applicationFailingOverEvent NOTIFICATION-TYPE
    OBJECTS {
                applicationIndex,
                applicationLPanIndex,
                applicationName,
                egeneraTrapSeverity,
                egeneraTrapMessage
            }
    STATUS      current
    DESCRIPTION
            "The notification generated when an application failover
            has been initiated.

            This trap is driven by 'application <lpanname>/<appname> Failover
            Started Event' event types.

            Severity: 3"

        ::=     { applicationNotifications 27 }


applicationFailedOverEvent NOTIFICATION-TYPE
    OBJECTS {
                applicationIndex,
                applicationLPanIndex,
                applicationName,
                egeneraTrapSeverity,
                egeneraTrapMessage
            }
    STATUS      current
    DESCRIPTION
            "The notification generated when an application failover
            has successfully completed.

            This trap is driven by 'application <lpanname>/<appname> Failover
            Completed Event' event types.

            Severity: 5"

        ::=     { applicationNotifications 28 }


applicationFailoverFailedEvent NOTIFICATION-TYPE
    OBJECTS {
                applicationIndex,
                applicationLPanIndex,
                applicationName,
                egeneraTrapSeverity,
                egeneraTrapMessage
            }
    STATUS      current
    DESCRIPTION
            "The notification generated when an application failover
            has failed.

            This trap is driven by 'application <lpanname>/<appname> Failover
            Failed Event' event types.

            Severity: 2"

        ::=     { applicationNotifications 29 }





-- health monitor induced actions
applicationFailureDetectedEvent NOTIFICATION-TYPE
    OBJECTS {
                applicationIndex,
                applicationLPanIndex,
                applicationName,
                egeneraTrapSeverity,
                egeneraTrapMessage
            }
    STATUS      current
    DESCRIPTION
            "The notification generated when an application health monitor
            has detected an application failure.  These failures are counted,
            and compared to 'restart after', 'failover after', and 'giveup
            after' thresholds of the health monitor to trigger application
            actions.

            This trap is driven by 'application <lpanname>/<appname> Health
            Monitor Detected Failure Event' event types.

            Severity: 4"

        ::=     { applicationNotifications 30 }


applicationRestartedEvent NOTIFICATION-TYPE
    OBJECTS {
                applicationIndex,
                applicationLPanIndex,
                applicationName,
                egeneraTrapSeverity,
                egeneraTrapMessage
            }
    STATUS      current
    DESCRIPTION
            "The notification generated when an application failures have
            been detected by the health monitor, and the 'restart' threshold
            has been reached or exceeded.  This results in an attempt to
            restart the application, for which further traps will be generated:

                applicationStartingEvent
                applicationStartedEvent
                applicationStartFailedEvent

            This trap is driven by 'application <lpanname>/<appname> Health
            Monitor Restart Event' event types.

            Severity: 3"

        ::=     { applicationNotifications 3 }


applicationFailoverEvent NOTIFICATION-TYPE
    OBJECTS {
                applicationIndex,
                applicationLPanIndex,
                applicationName,
                egeneraTrapSeverity,
                egeneraTrapMessage
            }
    STATUS      current
    DESCRIPTION
            "The notification generated when an application failures have
            been detected by the health monitor, and the 'failover' threshold
            has been reached or exceeded.  This results in an attempt to
            failover the application, for which further traps will be generated:

                applicationMovingEvent
                applicationMovedEvent
                applicationMoveFailedEvent

            This trap is driven by 'application <lpanname>/<appname> Health
            Monitor Failover Event' event types.

            Severity: 3"

        ::=     { applicationNotifications 4 }


applicationGiveupEvent NOTIFICATION-TYPE
    OBJECTS {
                applicationIndex,
                applicationLPanIndex,
                applicationName,
                egeneraTrapSeverity,
                egeneraTrapMessage
            }
    STATUS      current
    DESCRIPTION
            "The notification generated when an application failures have
            been detected by the health monitor, and the 'giveup' threshold
            has been reached or exceeded.  This results in the PAN Manager
            stop, for which further traps will be generated:

                applicationStoppingEvent
                applicationStoppedEvent
                applicationStopFailed

            This trap is driven by 'application <lpanname>/<appname> Health
            Monitor GiveUp Event' event types.

            Severity: 2"

        ::=     { applicationNotifications 5 }


applicationMonitorFailedEvent NOTIFICATION-TYPE
    OBJECTS {
                applicationIndex,
                applicationLPanIndex,
                applicationName,
                egeneraTrapSeverity,
                egeneraTrapMessage
            }
    STATUS      current
    DESCRIPTION
            "The notification generated when an application monitor failed,
            generally due to a missing PAN Agent.

            This trap is driven by 'application <lpanname>/<appname> Health
            Monitor Failed Event' event types.

            Severity: 3"


        ::=     { applicationNotifications 14 }


applicationMonitorRecoveredEvent NOTIFICATION-TYPE
    OBJECTS {
                applicationIndex,
                applicationLPanIndex,
                applicationName,
                egeneraTrapSeverity,
                egeneraTrapMessage
            }
    STATUS      current
    DESCRIPTION
            "The notification generated when an application monitor recovers,
            generally due to a restored PAN Agent.

            This trap is driven by 'application <lpanname>/<appname> Health Monitor
            Recovered Event' event types.

            Severity: 5"


        ::=     { applicationNotifications 15 }


applicationMonitorInvalidEvent NOTIFICATION-TYPE
    OBJECTS {
                applicationIndex,
                applicationLPanIndex,
                applicationName,
                egeneraTrapSeverity,
                egeneraTrapMessage
            }
    STATUS      current
    DESCRIPTION
            "The notification generated when an application monitor is,
            discovered to be invalid, generally due to misconfiguration.

            This trap is driven by 'application <lpanname>/<appname> Health
            Monitor Invalid Event' event types.

            Severity: 3"

        ::=     { applicationNotifications 16 }


applicationFailedEvent NOTIFICATION-TYPE
    OBJECTS {
                applicationIndex,
                applicationLPanIndex,
                applicationName,
                egeneraTrapSeverity,
                egeneraTrapMessage
            }
    STATUS      current
    DESCRIPTION
            "This trap is deprecated as of PAN Manager release 4.0.
            See the following more specific traps:

                applicationStartFailedEvent
                applicationStopFailed
                applicationMoveFailedEvent
                applicationRestartedEvent
                applicationFailoverEvent
                applicationGiveupEvent
            "

        ::=     { applicationNotifications 9 }


applicationConfigWarningEvent NOTIFICATION-TYPE
    OBJECTS {
                applicationIndex,
                applicationLPanIndex,
                applicationName,
                egeneraTrapSeverity,
                egeneraTrapMessage
            }
    STATUS      current
    DESCRIPTION
            "The notification generated when an application is
            potentially misconfigured.

            This trap is driven by 'application <lpanname>/<appname> Configuration
            Warning Event' event types.

            Severity: 3"

        ::=     { applicationNotifications 31 }


applicationStatusWarningEvent NOTIFICATION-TYPE
    OBJECTS {
                applicationIndex,
                applicationLPanIndex,
                applicationName,
                egeneraTrapSeverity,
                egeneraTrapMessage
            }
    STATUS      current
    DESCRIPTION
            "The notification generated when an application operation results in a
            potentially inappropriate state.

            This trap is driven by 'application <lpanname>/<appname> Status
            Warning Event' event types.

            Severity: 3"

        ::=     { applicationNotifications 32 }



-- load balancer traps mirror load balancerlication traps
-- load balancer create/modify/delete
loadBalancerCreatedEvent NOTIFICATION-TYPE
    OBJECTS {
                loadBalancerIndex,
                loadBalancerLPanIndex,
                loadBalancerName,
                egeneraTrapSeverity,
                egeneraTrapMessage
            }
    STATUS      current
    DESCRIPTION
            "The notification generated when a load balancer has been
            created.

            This trap is driven by 'LPAN <lpanname> load balancer Create
            Event' event types.

            Severity: 5"

        ::=     { applicationNotifications 40 }


loadBalancerModifyEvent NOTIFICATION-TYPE
    OBJECTS {
                loadBalancerIndex,
                loadBalancerLPanIndex,
                loadBalancerName,
                egeneraTrapSeverity,
                egeneraTrapMessage
            }
    STATUS      current
    DESCRIPTION
            "The notification generated when a load balancer is modified.

            This trap is driven by 'load balancer <lpanname>/<lbname>
            Changed Event' event types.

            Severity: 5"

        ::=     { applicationNotifications 41 }


loadBalancerDeletedEvent NOTIFICATION-TYPE
    OBJECTS {
                loadBalancerIndex,
                loadBalancerLPanIndex,
                loadBalancerName,
                egeneraTrapSeverity,
                egeneraTrapMessage
            }
    STATUS      current
    DESCRIPTION
            "The notification generated when a load balancer has been
            deleted.

            This trap is driven by 'LPAN <lpanname> load balancer Delete
            Event' event types.

            Severity: 5"

        ::=     { applicationNotifications 42 }


-- load balancer starting/started/start failed
loadBalancerStartingEvent NOTIFICATION-TYPE
    OBJECTS {
                loadBalancerIndex,
                loadBalancerLPanIndex,
                loadBalancerName,
                egeneraTrapSeverity,
                egeneraTrapMessage
            }
    STATUS      current
    DESCRIPTION
            "The notification generated when a load balancer start has been
            initiated.

            This trap is driven by 'load balancer <lpanname>/<lbname>
            Start Started Event' event types.

            Severity: 5"

        ::=     { applicationNotifications 43 }


loadBalancerStartedEvent NOTIFICATION-TYPE
    OBJECTS {
                loadBalancerIndex,
                loadBalancerLPanIndex,
                loadBalancerName,
                egeneraTrapSeverity,
                egeneraTrapMessage
            }
    STATUS      current
    DESCRIPTION
            "The notification generated when a load balancer has started
            successfully.

            This trap is driven by 'load balancer <lpanname>/<lbname>
            Start Completed Event ' event types.

            Severity: 5"

        ::=     { applicationNotifications 44 }


loadBalancerStartFailedEvent NOTIFICATION-TYPE
    OBJECTS {
                loadBalancerIndex,
                loadBalancerLPanIndex,
                loadBalancerName,
                egeneraTrapSeverity,
                egeneraTrapMessage
            }
    STATUS      current
    DESCRIPTION
            "The notification generated when a load balancer start attempt
            has failed.

            This trap is driven by 'load balancer <lpanname>/<lbname>
            Start Failed Event' event types.

            Severity: 2"

        ::=     { applicationNotifications 45 }


-- load balancer stopping/stopped/stop failed
loadBalancerStoppingEvent NOTIFICATION-TYPE
    OBJECTS {
                loadBalancerIndex,
                loadBalancerLPanIndex,
                loadBalancerName,
                egeneraTrapSeverity,
                egeneraTrapMessage
            }
    STATUS      current
    DESCRIPTION
            "The notification generated when a load balancer stop has been
            initiated.

            This trap is driven by 'load balancer <lpanname>/<lbname>
            Stop Started Event' event types.

            Severity: 5"

        ::=     { applicationNotifications 46 }


loadBalancerStoppedEvent NOTIFICATION-TYPE
    OBJECTS {
                loadBalancerIndex,
                loadBalancerLPanIndex,
                loadBalancerName,
                egeneraTrapSeverity,
                egeneraTrapMessage
            }
    STATUS      current
    DESCRIPTION
            "The notification generated when a load balancer has been
            successfully stopped.

            This trap is driven by 'load balancer <lpanname>/<lbname>
            Stop Completed Event' event types.

            Severity: 5"

        ::=     { applicationNotifications 47 }


loadBalancerStopFailedEvent NOTIFICATION-TYPE
    OBJECTS {
                loadBalancerIndex,
                loadBalancerLPanIndex,
                loadBalancerName,
                egeneraTrapSeverity,
                egeneraTrapMessage
            }
    STATUS      current
    DESCRIPTION
            "The notification generated when a load balancer has failed
            to stop.

            This trap is driven by 'load balancer <lpanname>/<lbname>
            Stop Failed Event' event types.

            Severity: 2"

        ::=     { applicationNotifications 48 }


-- load balancer moving/moved/move failed
loadBalancerMovingEvent NOTIFICATION-TYPE
    OBJECTS {
                loadBalancerIndex,
                loadBalancerLPanIndex,
                loadBalancerName,
                egeneraTrapSeverity,
                egeneraTrapMessage
            }
    STATUS      current
    DESCRIPTION
            "The notification generated when a load balancer move
            has been initiated.

            This trap is driven by 'load balancer <lpanname>/<lbname>
            Move Started Event' event types.

            Severity: 5"

        ::=     { applicationNotifications 49 }


loadBalancerMovedEvent NOTIFICATION-TYPE
    OBJECTS {
                loadBalancerIndex,
                loadBalancerLPanIndex,
                loadBalancerName,
                egeneraTrapSeverity,
                egeneraTrapMessage
            }
    STATUS      current
    DESCRIPTION
            "The notification generated when a load balancer move
            has successfully completed.

            This trap is driven by 'load balancer <lpanname>/<lbname>
            Move Completed Event' event types.

            Severity: 5"

        ::=     { applicationNotifications 50 }


loadBalancerMoveFailedEvent NOTIFICATION-TYPE
    OBJECTS {
                loadBalancerIndex,
                loadBalancerLPanIndex,
                loadBalancerName,
                egeneraTrapSeverity,
                egeneraTrapMessage
            }
    STATUS      current
    DESCRIPTION
            "The notification generated when a load balancer move
            has failed.

            This trap is driven by 'load balancer <lpanname>/<lbname>
            Move Failed Event' event types.

            Severity: 5"

        ::=     { applicationNotifications 51 }


-- load balancer failing over/failed over/failover failed
loadBalancerFailingOverEvent NOTIFICATION-TYPE
    OBJECTS {
                loadBalancerIndex,
                loadBalancerLPanIndex,
                loadBalancerName,
                egeneraTrapSeverity,
                egeneraTrapMessage
            }
    STATUS      current
    DESCRIPTION
            "The notification generated when a load balancer failover
            has been initiated.

            This trap is driven by 'load balancer <lpanname>/<lbname>
            Failover Started Event' event types.

            Severity: 5"

        ::=     { applicationNotifications 52 }


loadBalancerFailedOverEvent NOTIFICATION-TYPE
    OBJECTS {
                loadBalancerIndex,
                loadBalancerLPanIndex,
                loadBalancerName,
                egeneraTrapSeverity,
                egeneraTrapMessage
            }
    STATUS      current
    DESCRIPTION
            "The notification generated when a load balancer failover
            has successfully completed.

            This trap is driven by 'load balancer <lpanname>/<lbname>
            Failover Completed Event' event types.

            Severity: 5"

        ::=     { applicationNotifications 53 }


loadBalancerFailoverFailedEvent NOTIFICATION-TYPE
    OBJECTS {
                loadBalancerIndex,
                loadBalancerLPanIndex,
                loadBalancerName,
                egeneraTrapSeverity,
                egeneraTrapMessage
            }
    STATUS      current
    DESCRIPTION
            "The notification generated when a load balancer failover
            has failed.

            This trap is driven by 'load balancer <lpanname>/<lbname>
            Failover Failed Event' event types.

            Severity: 5"

        ::=     { applicationNotifications 54 }


-- health monitor induced actions
loadBalancerFailureDetectedEvent NOTIFICATION-TYPE
    OBJECTS {
                loadBalancerIndex,
                loadBalancerLPanIndex,
                loadBalancerName,
                egeneraTrapSeverity,
                egeneraTrapMessage
            }
    STATUS      current
    DESCRIPTION
            "The notification generated when a load balancer health monitor
            has detected a load balancer failure.  These failures are counted,
            and compared to 'restart after', 'failover after', and 'giveup
            after' thresholds of the health monitor to trigger load balancer
            actions.

            This trap is driven by 'load balancer <lpanname>/<lbname> Health
            Monitor Detected Failure Event' event types.

            Severity: 4"

        ::=     { applicationNotifications 61 }


loadBalancerRestartedEvent NOTIFICATION-TYPE
    OBJECTS {
                loadBalancerIndex,
                loadBalancerLPanIndex,
                loadBalancerName,
                egeneraTrapSeverity,
                egeneraTrapMessage
            }
    STATUS      current
    DESCRIPTION
            "The notification generated when a load balancer failures have
            been detected by the health monitor, and the 'restart' threshold
            has been reached or exceeded.  This results in an attempt to
            restart the load balancer, for which further traps will be generated:

                loadBalancerStartingEvent
                loadBalancerStartedEvent
                loadBalancerStartFailedEvent

            This trap is driven by 'load balancer <lpanname>/<lbname>
            Health Monitor Restart Event' event types.

            Severity: 5"

        ::=     { applicationNotifications 55 }


loadBalancerFailoverEvent NOTIFICATION-TYPE
    OBJECTS {
                loadBalancerIndex,
                loadBalancerLPanIndex,
                loadBalancerName,
                egeneraTrapSeverity,
                egeneraTrapMessage
            }
    STATUS      current
    DESCRIPTION
            "The notification generated when a load balancer failures have
            been detected by the health monitor, and the 'failover' threshold
            has been reached or exceeded.  This results in an attempt to
            failover the load balancer, for which further traps will be generated:

                loadBalancerMovingEvent
                loadBalancerMovedEvent
                loadBalancerMoveFailedEvent

            This trap is driven by 'load balancer <lpanname>/<lbname>
            Health Monitor Failover Event' event types.

            Severity: 5"

        ::=     { applicationNotifications 56 }


loadBalancerGiveupEvent NOTIFICATION-TYPE
    OBJECTS {
                loadBalancerIndex,
                loadBalancerLPanIndex,
                loadBalancerName,
                egeneraTrapSeverity,
                egeneraTrapMessage
            }
    STATUS      current
    DESCRIPTION
            "The notification generated when a load balancer failures have
            been detected by the health monitor, and the 'giveup' threshold
            has been reached or exceeded.  This results in the PAN Manager
            stop, for which further traps will be generated:

                loadBalancerStoppingEvent
                loadBalancerStoppedEvent
                loadBalancerStopFailed

            This trap is driven by 'load balancer <lpanname>/<lbname>
            Health Monitor GiveUp Event' event types.

            Severity: 5"

        ::=     { applicationNotifications 57 }


loadBalancerMonitorFailedEvent NOTIFICATION-TYPE
    OBJECTS {
                loadBalancerIndex,
                loadBalancerLPanIndex,
                loadBalancerName,
                egeneraTrapSeverity,
                egeneraTrapMessage
            }
    STATUS      current
    DESCRIPTION
            "The notification generated when a load balancer monitor failed,
            generally due to a missing PAN Agent.

            This trap is driven by 'load balancer <lpanname>/<lbname>
            Health Monitor Failed Event' event types.

            Severity: 2"


        ::=     { applicationNotifications 58 }


lbMonitorRecoveredEvent NOTIFICATION-TYPE
    OBJECTS {
                loadBalancerIndex,
                loadBalancerLPanIndex,
                loadBalancerName,
                egeneraTrapSeverity,
                egeneraTrapMessage
            }
    STATUS      current
    DESCRIPTION
            "The notification generated when a load balancer monitor recovers,
            generally due to a restored PAN Agent.

            This trap is driven by 'load balancer <lpanname>/<lbname> Health
            Monitor Recovered Event' event types.

            Severity: 5"


        ::=     { applicationNotifications 59 }


loadBalancerMonitorInvalidEvent NOTIFICATION-TYPE
    OBJECTS {
                loadBalancerIndex,
                loadBalancerLPanIndex,
                loadBalancerName,
                egeneraTrapSeverity,
                egeneraTrapMessage
            }
    STATUS      current
    DESCRIPTION
            "The notification generated when a load balancer monitor is,
            discovered to be invalid, generally due to misconfiguration.

            This trap is driven by 'load balancer <lpanname>/<lbname> Health
            Monitor Invalid Event' event types.

            Severity: 2"

        ::=     { applicationNotifications 60 }


loadBalancerConfigWarningEvent NOTIFICATION-TYPE
    OBJECTS {
                loadBalancerIndex,
                loadBalancerLPanIndex,
                loadBalancerName,
                egeneraTrapSeverity,
                egeneraTrapMessage
            }
    STATUS      current
    DESCRIPTION
            "The notification generated when a load balancer is
            potentially misconfigured.

            This trap is driven by 'application <lpanname>/<appname> Configuration
            Warning Event' event types.

            Severity: 3"

        ::=     { applicationNotifications 62 }


loadBalancerStatusWarningEvent NOTIFICATION-TYPE
    OBJECTS {
                loadBalancerIndex,
                loadBalancerLPanIndex,
                loadBalancerName,
                egeneraTrapSeverity,
                egeneraTrapMessage
            }
    STATUS      current
    DESCRIPTION
            "The notification generated when a load balancer operation results in a
            potentially inappropriate state.

            This trap is driven by 'application <lpanname>/<appname> Status
            Warning Event' event types.

            Severity: 3"

        ::=     { applicationNotifications 63 }


-- applicaion/load balancer resource traps (create/modify/delete for each resource)

nfsResourceCreateEvent NOTIFICATION-TYPE
    OBJECTS {
                nfsResourceIndex,
                nfsResourceLPANIndex,
                nfsResourceName,
                egeneraTrapSeverity,
                egeneraTrapMessage
            }
    STATUS      current
    DESCRIPTION
            "The notification generated when an nfs resource is created.

            This trap is driven by 'LPAN <lpanname> NFS resource Create
            Event' event types.

            Severity: 5"

        ::=     { applicationNotifications 71 }


nfsResourceModifyEvent NOTIFICATION-TYPE
    OBJECTS {
                nfsResourceIndex,
                nfsResourceLPANIndex,
                nfsResourceName,
                egeneraTrapSeverity,
                egeneraTrapMessage
            }
    STATUS      current
    DESCRIPTION
            "The notification generated when an nfs resource is created.

            This trap is driven by 'NFS resource <resourcename> Changed
            Event' event types.

            Severity: 5"

        ::=     { applicationNotifications 72 }


nfsResourceDeleteEvent NOTIFICATION-TYPE
    OBJECTS {
                nfsResourceIndex,
                nfsResourceLPANIndex,
                nfsResourceName,
                egeneraTrapSeverity,
                egeneraTrapMessage
            }
    STATUS      current
    DESCRIPTION
            "The notification generated when an nfs resource is deleted.

            This trap is driven by 'LPAN <lpanname> NFS resource Delete
            Event' event types.

            Severity: 5"

        ::=     { applicationNotifications 73 }


nfsResourceConfigWarningEvent NOTIFICATION-TYPE
    OBJECTS {
                nfsResourceIndex,
                nfsResourceLPANIndex,
                nfsResourceName,
                egeneraTrapSeverity,
                egeneraTrapMessage
            }
    STATUS      current
    DESCRIPTION
            "The notification generated when a failover policy is
            potentially misconfigured.

            This trap is driven by 'NFS resource  <resourcename>
            Configuration Warning Event' event types.

            Severity: 3"

        ::=     { applicationNotifications 89 }


scsiDiskResourceCreateEvent NOTIFICATION-TYPE
    OBJECTS {
                scsiDiskResourceIndex,
                scsiDiskResourceLPANIndex,
                scsiDiskResourceName,
                egeneraTrapSeverity,
                egeneraTrapMessage
            }
    STATUS      current
    DESCRIPTION
            "The notification generated when a scsi disk resource is created.

            This trap is driven by 'LPAN <lpanname> SCSI disk resource Create
            Event' event types.

            Severity: 5"

        ::=     { applicationNotifications 74 }


scsiDiskResourceModifyEvent NOTIFICATION-TYPE
    OBJECTS {
                scsiDiskResourceIndex,
                scsiDiskResourceLPANIndex,
                scsiDiskResourceName,
                egeneraTrapSeverity,
                egeneraTrapMessage
            }
    STATUS      current
    DESCRIPTION
            "The notification generated when a scsi disk resource is created.

            This trap is driven by 'SCSI disk resource <resourcename> Changed
            Event' event types.

            Severity: 5"

        ::=     { applicationNotifications 75 }


scsiDiskResourceDeleteEvent NOTIFICATION-TYPE
    OBJECTS {
                scsiDiskResourceIndex,
                scsiDiskResourceLPANIndex,
                scsiDiskResourceName,
                egeneraTrapSeverity,
                egeneraTrapMessage
            }
    STATUS      current
    DESCRIPTION
            "The notification generated when a scsi disk resource is deleted.

            This trap is driven by 'LPAN <lpanname> SCSI disk resource Delete
            Event' event types.

            Severity: 5"

        ::=     { applicationNotifications 76 }



scsiDiskResourceConfigWarningEvent NOTIFICATION-TYPE
    OBJECTS {
                scsiDiskResourceIndex,
                scsiDiskResourceLPANIndex,
                scsiDiskResourceName,
                egeneraTrapSeverity,
                egeneraTrapMessage
            }
    STATUS      current
    DESCRIPTION
            "The notification generated when a failover policy is
            potentially misconfigured.

            This trap is driven by 'SCSI disk resource <resourcename>
            Configuration Warning Event' event types.

            Severity: 3"

        ::=     { applicationNotifications 90 }



networkResourceCreateEvent NOTIFICATION-TYPE
    OBJECTS {
                networkResourceIndex,
                networkResourceLPANIndex,
                networkResourceName,
                egeneraTrapSeverity,
                egeneraTrapMessage
            }
    STATUS      current
    DESCRIPTION
            "The notification generated when a network resource is created.

            This trap is driven by 'LPAN <lpanname> network resource Create
            Event' event types.

            Severity: 5"

        ::=     { applicationNotifications 77 }


networkResourceModifyEvent NOTIFICATION-TYPE
    OBJECTS {
                networkResourceIndex,
                networkResourceLPANIndex,
                networkResourceName,
                egeneraTrapSeverity,
                egeneraTrapMessage
            }
    STATUS      current
    DESCRIPTION
            "The notification generated when a network resource is created.

            This trap is driven by 'network resource <resourcename> Changed
            Event' event types.

            Severity: 5"

        ::=     { applicationNotifications 78 }


networkResourceDeleteEvent NOTIFICATION-TYPE
    OBJECTS {
                networkResourceIndex,
                networkResourceLPANIndex,
                networkResourceName,
                egeneraTrapSeverity,
                egeneraTrapMessage
            }
    STATUS      current
    DESCRIPTION
            "The notification generated when a network resource is deleted.

            This trap is driven by 'LPAN <lpanname> network resource Delete
            Event' event types.

            Severity: 5"

        ::=     { applicationNotifications 79 }


networkResourceConfigWarningEvent NOTIFICATION-TYPE
    OBJECTS {
                networkResourceIndex,
                networkResourceLPANIndex,
                networkResourceName,
                egeneraTrapSeverity,
                egeneraTrapMessage
            }
    STATUS      current
    DESCRIPTION
            "The notification generated when a failover policy is
            potentially misconfigured.

            This trap is driven by 'network resource <resourcename>
            Configuration Warning Event' event types.

            Severity: 3"

        ::=     { applicationNotifications 91 }



failoverPolicyCreateEvent NOTIFICATION-TYPE
    OBJECTS {
                failoverPolicyIndex,
                failoverPolicyLPANIndex,
                failoverPolicyName,
                egeneraTrapSeverity,
                egeneraTrapMessage
            }
    STATUS      current
    DESCRIPTION
            "The notification generated when a failover policy is created.

            This trap is driven by 'LPAN <lpanname> failover policy Create
            Event' event types.

            Severity: 5"

        ::=     { applicationNotifications 80 }


failoverPolicyModifyEvent NOTIFICATION-TYPE
    OBJECTS {
                failoverPolicyIndex,
                failoverPolicyLPANIndex,
                failoverPolicyName,
                egeneraTrapSeverity,
                egeneraTrapMessage
            }
    STATUS      current
    DESCRIPTION
            "The notification generated when a failover policy is created.

            This trap is driven by 'failover policy <resourcename> Changed
            Event' event types.

            Severity: 5"

        ::=     { applicationNotifications 81 }


failoverPolicyDeleteEvent NOTIFICATION-TYPE
    OBJECTS {
                failoverPolicyIndex,
                failoverPolicyLPANIndex,
                failoverPolicyName,
                egeneraTrapSeverity,
                egeneraTrapMessage
            }
    STATUS      current
    DESCRIPTION
            "The notification generated when a failover policy is deleted.

            This trap is driven by 'LPAN <lpanname> failover policy Delete
            Event' event types.

            Severity: 5"

        ::=     { applicationNotifications 82 }


failoverPolicyConfigWarningEvent NOTIFICATION-TYPE
    OBJECTS {
                failoverPolicyIndex,
                failoverPolicyLPANIndex,
                failoverPolicyName,
                egeneraTrapSeverity,
                egeneraTrapMessage
            }
    STATUS      current
    DESCRIPTION
            "The notification generated when a failover policy is
            potentially misconfigured.

            This trap is driven by 'failover policy <resourcename>
            Configuration Warning Event' event types.

            Severity: 3"

        ::=     { applicationNotifications 92 }



executableResourceCreateEvent NOTIFICATION-TYPE
    OBJECTS {
                executableResourceIndex,
                executableResourceLPANIndex,
                executableResourceName,
                egeneraTrapSeverity,
                egeneraTrapMessage
            }
    STATUS      current
    DESCRIPTION
            "The notification generated when an executable resource is created.

            This trap is driven by 'LPAN <lpanname> executable resource Create
            Event' event types.

            Severity: 5"

        ::=     { applicationNotifications 83 }


executableResourceModifyEvent NOTIFICATION-TYPE
    OBJECTS {
                executableResourceIndex,
                executableResourceLPANIndex,
                executableResourceName,
                egeneraTrapSeverity,
                egeneraTrapMessage
            }
    STATUS      current
    DESCRIPTION
            "The notification generated when an executable resource is created.

            This trap is driven by 'executable resource <resourcename> Changed
            Event' event types.

            Severity: 5"

        ::=     { applicationNotifications 84 }


executableResourceDeleteEvent NOTIFICATION-TYPE
    OBJECTS {
                executableResourceIndex,
                executableResourceLPANIndex,
                executableResourceName,
                egeneraTrapSeverity,
                egeneraTrapMessage
            }
    STATUS      current
    DESCRIPTION
            "The notification generated when an executable resource is deleted.

            This trap is driven by 'LPAN <lpanname> executable resource Delete
            Event' event types.

            Severity: 5"

        ::=     { applicationNotifications 85 }


executableResourceConfigWarningEvent NOTIFICATION-TYPE
    OBJECTS {
                executableResourceIndex,
                executableResourceLPANIndex,
                executableResourceName,
                egeneraTrapSeverity,
                egeneraTrapMessage
            }
    STATUS      current
    DESCRIPTION
            "The notification generated when an executable resource is
            potentially misconfigured.

            This trap is driven by 'executable resource <resourcename>
            Configuration Warning Event' event types.

            Severity: 3"

        ::=     { applicationNotifications 93 }



healthMonitorCreateEvent NOTIFICATION-TYPE
    OBJECTS {
                healthMonitorIndex,
                healthMonitorLPANIndex,
                healthMonitorName,
                egeneraTrapSeverity,
                egeneraTrapMessage
            }
    STATUS      current
    DESCRIPTION
            "The notification generated when an health monitor is created.

            This trap is driven by 'LPAN <lpanname> health monitor Create
            Event' event types.

            Severity: 5"

        ::=     { applicationNotifications 86 }


healthMonitorModifyEvent NOTIFICATION-TYPE
    OBJECTS {
                healthMonitorIndex,
                healthMonitorLPANIndex,
                healthMonitorName,
                egeneraTrapSeverity,
                egeneraTrapMessage
            }
    STATUS      current
    DESCRIPTION
            "The notification generated when an health monitor is created.

            This trap is driven by 'health monitor <resourcename> Changed
            Event' event types.

            Severity: 5"

        ::=     { applicationNotifications 87 }


healthMonitorDeleteEvent NOTIFICATION-TYPE
    OBJECTS {
                healthMonitorIndex,
                healthMonitorLPANIndex,
                healthMonitorName,
                egeneraTrapSeverity,
                egeneraTrapMessage
            }
    STATUS      current
    DESCRIPTION
            "The notification generated when an health monitor is deleted.

            This trap is driven by 'LPAN <lpanname> health monitor Delete
            Event' event types.

            Severity: 5"

        ::=     { applicationNotifications 88 }


healthMonitorConfigWarningEvent NOTIFICATION-TYPE
    OBJECTS {
                healthMonitorIndex,
                healthMonitorLPANIndex,
                healthMonitorName,
                egeneraTrapSeverity,
                egeneraTrapMessage
            }
    STATUS      current
    DESCRIPTION
            "The notification generated when a health monitor is
            potentially misconfigured.

            This trap is driven by 'health monitor <resourcename>
            Configuration Warning Event' event types.

            Severity: 3"

        ::=     { applicationNotifications 94 }



egeneraUserNotifications OBJECT IDENTIFIER ::= { egeneraNotifications 12 }


userCreatedEvent NOTIFICATION-TYPE
    OBJECTS {
                userIndex,
                userName,
                egeneraTrapSeverity,
                egeneraTrapMessage
            }
    STATUS      current
    DESCRIPTION
            "The notification generated when a user has been created.

            This trap is driven by 'User Added Event' event types.

            Severity: 5"

        ::=     { egeneraUserNotifications 1 }


userDeletedEvent NOTIFICATION-TYPE
    OBJECTS {
                userIndex,
                userName,
                egeneraTrapSeverity,
                egeneraTrapMessage
            }
    STATUS      current
    DESCRIPTION
            "The notification generated when a user has been deleted.

            This trap is driven by 'User Deleted Event' event types.

            Severity: 5"

        ::=     { egeneraUserNotifications 2 }


userLoginEvent NOTIFICATION-TYPE
    OBJECTS {
                userIndex,
                userName,
                egeneraTrapSeverity,
                egeneraTrapMessage
            }
    STATUS      current
    DESCRIPTION
            "The notification generated when a user has logged in to the PAN
            Manager.

            This trap is deprecated, as there is no underlying even to drive
            the trap.  The definition exists to satisfy early requirements
            documents."

        ::=     { egeneraUserNotifications 3 }


userLogoutEvent NOTIFICATION-TYPE
    OBJECTS {
                userIndex,
                userName,
                egeneraTrapSeverity,
                egeneraTrapMessage
            }
    STATUS      current
    DESCRIPTION
            "The notification generated when a user has logged out of the PAN
            Manager.

            This trap is deprecated, as there is no underlying even to drive
            the trap.  The definition exists to satisfy early requirements
            documents."

        ::=     { egeneraUserNotifications 4 }


userModifiedEvent NOTIFICATION-TYPE
    OBJECTS {
                userIndex,
                userName,
                egeneraTrapSeverity,
                egeneraTrapMessage
            }
    STATUS      current
    DESCRIPTION
            "The notification generated when a user has been modified.

            This trap is driven by 'User Modified Event' event types.

            Severity: 5"

        ::=     { egeneraUserNotifications 5 }


egeneraAuthenticationNotifications OBJECT IDENTIFIER ::= { egeneraNotifications 13 }

invalidManagerRequestEvent NOTIFICATION-TYPE
    OBJECTS {
                snmpManagerAddress,
                egeneraTrapSeverity,
                egeneraTrapMessage
            }
    STATUS      current
    DESCRIPTION
            "The notification generated when an unauthorized SNMP manager
            sends a request to the agent.

            This event is driven by incoming SNMP packets, and currently is
            not logged."

        ::=     { egeneraAuthenticationNotifications 1 }


invalidCommStringRequestEvent NOTIFICATION-TYPE
    OBJECTS {
                snmpManagerAddress,
                egeneraTrapSeverity,
                egeneraTrapMessage
            }
    STATUS      current
    DESCRIPTION
            "The notification generated when an authorized SNMP manager
            sends a request containing an invalid community string.

            This event is driven by incoming SNMP packets, and currently is
            not logged."

        ::=     { egeneraAuthenticationNotifications 2 }


pimNotifications OBJECT IDENTIFIER ::= { egeneraNotifications 14 }

pimSelectedEvent NOTIFICATION-TYPE
    OBJECTS {
                pimIndex,
                pimFrameIndex,
                pimName,
                egeneraTrapSeverity,
                egeneraTrapMessage
            }
    STATUS      current
    DESCRIPTION
            "The notification generated when a pim has been selected.

             This trap is driven by 'PIM <framename>/pim<1..4> Selected Status
             true Event' event types.

             Severity: 5"

        ::=     { pimNotifications 1 }

pimDeselectedEvent NOTIFICATION-TYPE
    OBJECTS {
                pimIndex,
                pimFrameIndex,
                pimName,
                egeneraTrapSeverity,
                egeneraTrapMessage
            }
    STATUS      current
    DESCRIPTION
            "The notification generated when a pim has been unselected.

             This trap is driven by 'PIM <framename>/pim<1..4> Selected Status
             false Event' even types.

             Severity: 5"

        ::=     { pimNotifications 2 }


pimPowerThresholdHighEvent NOTIFICATION-TYPE
    OBJECTS {
                pimIndex,
                pimFrameIndex,
                pimName,
                egeneraTrapSeverity,
                egeneraTrapMessage
            }
    STATUS      current
    DESCRIPTION
            "The notification generated when a pim's power threshold is high.

             This trap is driven by 'PIM <framename>/pim<1..4> Power Threshold High' event types.

             Severity: 3"

        ::=     { pimNotifications 3 }


pimCurrentThresholdHighEvent NOTIFICATION-TYPE
    OBJECTS {
                pimIndex,
                pimFrameIndex,
                pimName,
                egeneraTrapSeverity,
                egeneraTrapMessage
            }
    STATUS      current
    DESCRIPTION
            "The notification generated when a pim's current threshold is high.

             This trap is driven by 'PIM <framename>/pim<1..4> Current Threshold High' event types.

             Severity: 3"

        ::=     { pimNotifications 4 }


pimSourceTransitionEvent NOTIFICATION-TYPE
    OBJECTS {
                pimIndex,
                pimFrameIndex,
                pimName,
                egeneraTrapSeverity,
                egeneraTrapMessage
            }
    STATUS      current
    DESCRIPTION
            "The notification generated when a pim's source transition happened.

             This trap is driven by 'PIM <framename>/pim<1..4> Source Transition' event types.

             Severity: 4"

        ::=     { pimNotifications 5 }

pimInsertedEvent NOTIFICATION-TYPE
    OBJECTS {
                pimIndex,
                pimFrameIndex,
                pimName,
                egeneraTrapSeverity,
                egeneraTrapMessage
            }
    STATUS      current
    DESCRIPTION
            "The notification generated when a pim is inserted.

             This trap is driven by 'PIM <framename>/pim<1..4> Inserted' event types.

             Severity: 5"

        ::=     { pimNotifications 6 }


pimRemovedEvent NOTIFICATION-TYPE
    OBJECTS {
                pimIndex,
                pimFrameIndex,
                pimName,
                egeneraTrapSeverity,
                egeneraTrapMessage
            }
    STATUS      current
    DESCRIPTION
            "The notification generated when a pim is ejected.

             This trap is driven by 'PIM <framename>/pim<1..4> Removed' event types.

             Severity: 5"

        ::=     { pimNotifications 7 }


pimSourcePreferenceConfiguredEvent NOTIFICATION-TYPE
    OBJECTS {
                pimIndex,
                pimFrameIndex,
                pimName,
                egeneraTrapSeverity,
                egeneraTrapMessage
            }
    STATUS      current
    DESCRIPTION
            "The notification generated when a pim source preference is configured.

             This trap is driven by 'PIM <framename>/pim<1..4> Source Preference configured' event types.

             Severity: 5"

        ::=     { pimNotifications 8 }


pimConfigErrorEvent NOTIFICATION-TYPE
    OBJECTS {
                pimIndex,
                pimFrameIndex,
                pimName,
                egeneraTrapSeverity,
                egeneraTrapMessage
            }
    STATUS      current
    DESCRIPTION
             "The notification generated when a pim encounters an error activating a configuration changea.

             This trap is driven by 'PIM <framename>/pim<1..4> Config Error Event' event types.

             Severity: 2"

        ::=     { pimNotifications 9 }


pimPowerOnEvent NOTIFICATION-TYPE
    OBJECTS {
                pimIndex,
                pimFrameIndex,
                pimName,
                egeneraTrapSeverity,
                egeneraTrapMessage
            }
    STATUS      current
    DESCRIPTION
            "The notification generated when an pim is powered on.

            This trap is driven by 'Blade <framename>/pim<1..4> Power Status Event'
            event types describing power on events.

            Since the underlying event type describes pim power on and off
            events, enabling/disabling this SNMP trap as an event action is bound
            to the enabling/disabling of pimPowerOffEvent.

            Severity: 5"

        ::=     { pimNotifications 10 }


pimPowerOffEvent NOTIFICATION-TYPE
    OBJECTS {
                pimIndex,
                pimFrameIndex,
                pimName,
                egeneraTrapSeverity,
                egeneraTrapMessage
            }
    STATUS      current
    DESCRIPTION
            "The notification generated when an pim is powered off.

            This trap is driven by 'Blade <framename>/pim<1..4> Power Status Event'
            event types describing power on events.

            Since the underlying event type describes pim power on and off
            events, enabling/disabling this SNMP trap as an event action is bound
            to the enabling/disabling of pimPowerOnEvent.

            Severity: 5"

        ::=     { pimNotifications 11 }


pimEnabledEvent NOTIFICATION-TYPE
    OBJECTS {
                pimIndex,
                pimFrameIndex,
                pimName,
                egeneraTrapSeverity,
                egeneraTrapMessage
            }
    STATUS      current
    DESCRIPTION
            "The notification generated when an pim is enabled (returns
             to service).

             This trap is driven by 'Blade <framename>/pim<1..4> Out of Service Status
             false Event' event types.

             Severity: 5"

        ::=     { pimNotifications 12 }


pimDisabledEvent NOTIFICATION-TYPE
    OBJECTS {
                pimIndex,
                pimFrameIndex,
                pimName,
                egeneraTrapSeverity,
                egeneraTrapMessage
            }
    STATUS      current
    DESCRIPTION
            "The notification generated when an pim is disabled. (removed
             from service).

             This trap is driven by 'Blade <framename>/pim<1..4> Out of Service Status
             true Event' event types.

             Severity: 5"

        ::=     { pimNotifications 13 }


pimOutOfServicePendingEvent NOTIFICATION-TYPE
    OBJECTS {
                pimIndex,
                pimFrameIndex,
                pimName,
                egeneraTrapSeverity,
                egeneraTrapMessage
            }
    STATUS      current
    DESCRIPTION
            "The notification generated when a pBlade enters the 'out of service
            pending' state.

            This trap is driven by 'cBlade <bladeframe>/pim<1..4> Out of Service Pending
            Event' event types

            Severity: 5"

        ::=     { pimNotifications 14 }



pimPowerOnOpEvent NOTIFICATION-TYPE
    OBJECTS {
                pimIndex,
                pimFrameIndex,
                pimName,
                egeneraTrapSeverity,
                egeneraTrapMessage
            }
    STATUS      current
    DESCRIPTION
            "Encapsulates pim power on operation event.

            This trap is driven by 'pim <framename>/pim<1..4> Hardware Operation
            Event' event types.

            Since the underlying event type describes pim power on and off
            operation events, enabling/disabling this SNMP trap as an event action
            is bound to the enabling/disabling of pimPowerOffOpEvent,
            pimPowerCycleEvent, and pimResetOpEvent.

            Severity: 5"

        ::=     { pimNotifications 15 }


pimPowerOffOpEvent NOTIFICATION-TYPE
    OBJECTS {
                pimIndex,
                pimFrameIndex,
                pimName,
                egeneraTrapSeverity,
                egeneraTrapMessage
            }
    STATUS      current
    DESCRIPTION
            "Encapsulates pim power off operation event.

            This trap is driven by 'pim <framename>/pim<1..4> Hardware Operation
            Event' event types.

            Since the underlying event type describes pim power on and off
            operation events, enabling/disabling this SNMP trap as an event action
            is bound to the enabling/disabling of pimPowerOnOpEvent,
            pimPowerCycleEvent, and pimResetOpEvent.

            Severity: 5"

        ::=     { pimNotifications 16 }


pimPowerCycleOpEvent NOTIFICATION-TYPE
    OBJECTS {
                pimIndex,
                pimFrameIndex,
                pimName,
                egeneraTrapSeverity,
                egeneraTrapMessage
            }
    STATUS      current
    DESCRIPTION
            "Encapsulates pim power cycle operation event.

            This trap is driven by 'pim <framename>/pim<1..4> Hardware Operation
            Event' event types.

            Since the underlying event type describes pim power on and off
            operation events, enabling/disabling this SNMP trap as an event action
            is bound to the enabling/disabling of pimPowerOnOpEvent,
            pimPowerCycleEvent, and pimResetOpEvent.

            Severity: 5"

        ::=     { pimNotifications 17 }


pimResetOpEvent NOTIFICATION-TYPE
    OBJECTS {
                pimIndex,
                pimFrameIndex,
                pimName,
                egeneraTrapSeverity,
                egeneraTrapMessage
            }
    STATUS      current
    DESCRIPTION
            "Encapsulates pim reset operation event.

            This trap is driven by 'pim <framename>/pim<1..4> Hardware Operation
            Event' event types.

            Since the underlying event type describes pim power on and off
            operation events, enabling/disabling this SNMP trap as an event action
            is bound to the enabling/disabling of pimPowerOnOpEvent,
            pimPowerCycleEvent, and pimPowerCycleOpEvent.

            Severity: 5"

        ::=     { pimNotifications 18 }


pimHwEventEvent NOTIFICATION-TYPE
    OBJECTS {
                pimIndex,
                pimFrameIndex,
                pimName,
                egeneraTrapSeverity,
                egeneraTrapMessage
            }
    STATUS      current
    DESCRIPTION
            "Encapsulates generic events from hardware.

            This trap is driven by 'Blade <framename>/pim<1..4> non-sensor Event'
            event types.

            Severity: 3"

        ::=     { pimNotifications 19 }


pimVoltageUpperEvent NOTIFICATION-TYPE
    OBJECTS {
                pimIndex,
                pimFrameIndex,
                pimName,
                sensorName,
                sensorThreshold,
                sensorValue,
                egeneraTrapSeverity,
                egeneraTrapMessage
            }
    STATUS      current
    DESCRIPTION
            "Encapsulates pim critical high voltage sensor events.

            This trap is driven by 'Blade <framename>/pim<1..4> <voltage-sensor-name>
            Critical High Event' event types.

            The sensorValue and sensorThreshold fields are ingeter representations
            of real numbers.  The real numbers are multiplied by 100 and rounded
            to produce an integer, thus 0.530 => 53.

            This trap replaces pimHwThreshEvent.

            Severity: 3"

        ::=     { pimNotifications 20 }


pimVoltageLowerEvent NOTIFICATION-TYPE
    OBJECTS {
                pimIndex,
                pimFrameIndex,
                pimName,
                sensorName,
                sensorThreshold,
                sensorValue,
                egeneraTrapSeverity,
                egeneraTrapMessage
            }
    STATUS      current
    DESCRIPTION
            "Encapsulates pim critical low voltage sensor events.

            This trap is driven by 'Blade <framename>/pim<1..4> <voltage-sensor-name>
            Critical Low Event' event types.

            The sensorValue and sensorThreshold fields are ingeter representations
            of real numbers.  The real numbers are multiplied by 100 and rounded
            to produce an integer, thus 0.530 => 53.

            This trap replaces pimHwThreshEvent.

            Severity: 3"

        ::=     { pimNotifications 21 }


pimFanSpeedUpperEvent NOTIFICATION-TYPE
    OBJECTS {
                pimIndex,
                pimFrameIndex,
                pimName,
                sensorName,
                sensorThreshold,
                sensorValue,
                egeneraTrapSeverity,
                egeneraTrapMessage
            }
    STATUS      current
    DESCRIPTION
            "Encapsulates pim critical high fan speed  sensor events.

            This trap is driven by 'Blade <framename>/pim<1..4> <fan-sensor-name>
            Critical High Event' event types.

            This trap replaces pimHwThreshEvent.

            Severity: 3"

        ::=     { pimNotifications 22 }


pimFanSpeedLowerEvent NOTIFICATION-TYPE
    OBJECTS {
                pimIndex,
                pimFrameIndex,
                pimName,
                sensorName,
                sensorThreshold,
                sensorValue,
                egeneraTrapSeverity,
                egeneraTrapMessage
            }
    STATUS      current
    DESCRIPTION
            "Encapsulates pim critical low fan speed sensor events.

            This trap is driven by 'Blade <framename>/pim<1..4> <fan-sensor-name>
            Critical Low Event' event types.

            This trap replaces pimHwThreshEvent.

            Severity: 3"

        ::=     { pimNotifications 23 }



pimTempUpperEvent NOTIFICATION-TYPE
    OBJECTS {
                pimIndex,
                pimFrameIndex,
                pimName,
                sensorName,
                sensorThreshold,
                sensorValue,
                egeneraTrapSeverity,
                egeneraTrapMessage
            }
    STATUS      current
    DESCRIPTION
            "Encapsulates pim critical high temperature sensor events.

            This trap is driven by 'Blade <framename>/pim<1..4> <temp-sensor-name>
            Critical High Event' event types.

            This trap replaces pimHwThreshEvent.

            Severity: 3"

        ::=     { pimNotifications 24 }


pimTempLowerEvent NOTIFICATION-TYPE
    OBJECTS {
                pimIndex,
                pimFrameIndex,
                pimName,
                sensorName,
                sensorThreshold,
                sensorValue,
                egeneraTrapSeverity,
                egeneraTrapMessage
            }
    STATUS      current
    DESCRIPTION
            "Encapsulates pim critical low temperature sensor events.

            This trap is driven by 'Blade <framename>/pim<1..4> <temp-sensor-name>
            Critical Low Event' event types.

            This     trap replaces pimHwThreshEvent.

            Severity: 3"

        ::=     { pimNotifications 25 }


poolNotifications OBJECT IDENTIFIER ::= { egeneraNotifications 15 }

globalPoolCreatedEvent NOTIFICATION-TYPE
    OBJECTS {
                poolIndex,
                poolName,
                egeneraTrapSeverity,
                egeneraTrapMessage
            }
    STATUS      current
    DESCRIPTION
            "The notification generated when a global pool is created.

             Severity: 5"

        ::=     { poolNotifications 1 }

globalPoolDeletedEvent NOTIFICATION-TYPE
    OBJECTS {
                poolIndex,
                poolName,
                egeneraTrapSeverity,
                egeneraTrapMessage
            }
    STATUS      current
    DESCRIPTION
            "The notification generated when a global pool is deleted.

             Severity: 5"

        ::=     { poolNotifications 2 }

localPoolCreatedEvent NOTIFICATION-TYPE
    OBJECTS {
                poolIndex,
                poolName,
                egeneraTrapSeverity,
                egeneraTrapMessage
            }
    STATUS      current
    DESCRIPTION
            "The notification generated when a local pool is created.

             Severity: 5"

        ::=     { poolNotifications 3 }

localPoolDeletedEvent NOTIFICATION-TYPE
    OBJECTS {
                poolIndex,
                poolName,
                egeneraTrapSeverity,
                egeneraTrapMessage
            }
    STATUS      current
    DESCRIPTION
            "The notification generated when a local pool is deleted.

             Severity: 5"

        ::=     { poolNotifications 4 }


poolConfigChangedEvent NOTIFICATION-TYPE
    OBJECTS {
                poolIndex,
                poolName,
                egeneraTrapSeverity,
                egeneraTrapMessage
            }
    STATUS      current
    DESCRIPTION
            "The notification generated when a global configuration is changed.

             Severity: 5"

        ::=     { poolNotifications 5 }

poolPBladeArrivedEvent NOTIFICATION-TYPE
    OBJECTS {
                poolIndex,
                poolName,
                egeneraTrapSeverity,
                egeneraTrapMessage
            }
    STATUS      current
    DESCRIPTION
            "The notification generated when a pool pBlade is arrived.

             Severity: 5"

        ::=     { poolNotifications 6 }

poolPBladeDepartedEvent NOTIFICATION-TYPE
    OBJECTS {
                poolIndex,
                poolName,
                egeneraTrapSeverity,
                egeneraTrapMessage
            }
    STATUS      current
    DESCRIPTION
            "The notification generated when a pool pBlade is departed.

             Severity: 5"

        ::=     { poolNotifications 7 }


diskNotifications OBJECT IDENTIFIER ::= { egeneraNotifications 16 }

diskPartitionedEvent NOTIFICATION-TYPE
    OBJECTS {
                diskIdOctets,
                diskId,
                egeneraTrapSeverity,
                egeneraTrapMessage
            }
    STATUS      current
    DESCRIPTION
            "The notification generated when a disk is partitioned.

             Severity: 5"

        ::=     { diskNotifications 1 }

diskWinPeEvent NOTIFICATION-TYPE
    OBJECTS {
                diskIdOctets,
                diskId,
                egeneraTrapSeverity,
                egeneraTrapMessage
            }
    STATUS      current
    DESCRIPTION
            "The notification generated when the WinPe image is installed on a disk.

             Severity: 5"

        ::=     { diskNotifications 2 }

diskRootedEvent NOTIFICATION-TYPE
    OBJECTS {
                diskIdOctets,
                diskId,
                egeneraTrapSeverity,
                egeneraTrapMessage
            }
    STATUS      current
    DESCRIPTION
            "The notification generated when a root image is installed on a disk.

             Severity: 5"

        ::=     { diskNotifications 3 }

diskOpEvent NOTIFICATION-TYPE
    OBJECTS {
                diskIdOctets,
                diskId,
                egeneraTrapSeverity,
                egeneraTrapMessage
            }
    STATUS      current
    DESCRIPTION
            "The notification generated when an operation is performed on a disk

             Severity: 5"

        ::=     { diskNotifications 4 }

vBladeNotifications OBJECT IDENTIFIER ::= { egeneraNotifications 17 }



vBladePowerOnEvent NOTIFICATION-TYPE
    OBJECTS {
                vBladeIndex,
                vBladePBladeIndex,
                vBladeFrameIndex,
                vBladeName,
                egeneraTrapSeverity,
                egeneraTrapMessage
            }
    STATUS      current
    DESCRIPTION
            "The notification generated when a vBlade is powered on.

            This trap is driven by 'Blade <framename>/p<1|2> Power Status Event'
            event types describing power on events.

            Since the underlying event type describes vBlade power on and off
            events, enabling/disabling this SNMP trap as an event action is bound
            to the enabling/disabling of vBladePowerOffEvent.

            Severity: 5"

        ::=     { vBladeNotifications 3 }


vBladePowerOffEvent NOTIFICATION-TYPE
    OBJECTS {
                vBladeIndex,
                vBladePBladeIndex,
                vBladeFrameIndex,
                vBladeName,
                egeneraTrapSeverity,
                egeneraTrapMessage
            }
    STATUS      current
    DESCRIPTION
            "The notification generated when a vBlade is powered off.

            This trap is driven by 'Blade <framename>/p<1|2> Power Status Event'
            event types describing power on events.

            Since the underlying event type describes sBlade power on and off
            events, enabling/disabling this SNMP trap as an event action is bound
            to the enabling/disabling of vBladePowerOnEvent.

            Severity: 5"

        ::=     { vBladeNotifications 4 }



vBladeShutdownEvent NOTIFICATION-TYPE
    OBJECTS {
                vBladeIndex,
                vBladePBladeIndex,
                vBladeFrameIndex,
                vBladeName,
                egeneraTrapSeverity,
                egeneraTrapMessage
            }
    STATUS      current
    DESCRIPTION
            "The notification generated when a vBlade has been shut
             down.

            This trap is driven by 'blade.status.monitor.event' event types
            that describe a vBlade transition from the shutting down state to
            the shutdown state.

            This event type is not user visible, and will not appear in
            CLI or GUI event quieries.  The trap exists to satisfy early
            requirements documents.

            Severity: 5"

        ::=     { vBladeNotifications 6 }




vBladeHwEvent NOTIFICATION-TYPE
    OBJECTS {
                vBladeIndex,
                vBladePBladeIndex,
                vBladeFrameIndex,
                vBladeName,
                egeneraTrapSeverity,
                egeneraTrapMessage
            }
    STATUS      current
    DESCRIPTION
            "Encapsulates generic events from hardware.

            This trap is driven by 'Blade <framename>/p<1..24> non-sensor Event'
            event types that do not indicate panic, commanded shutdown,
            commanded reboot, or init level events.  Examples message contents
            include:

            OEM Type 0xe0, value = 0x64:0x21:0xce:0xe0:0x1d:0x00:0x00:0x00...
            bmc reset
            deasserted, value = 0x0211
            system booted

            Contact EES for more specific information.

            Since the underlying event type describes vBlade all non-sensor hardware
            events, and since there are specific traps for panic, commanded shutdown,
            commanded reboot, and init level events, enabling/disabling this SNMP trap
            as an event action is bound to the enabling/disabling of vBladePanicEvent,
            vBladeCmdShutdownEvent, vBladeCmdRebootEvent, vBladeCmdHaltEvent, and
            vBladeInitEvent.

            Severity: 3"

        ::=     { vBladeNotifications 11}

vBladeCmdRebootEvent NOTIFICATION-TYPE
     OBJECTS {
                 vBladeIndex,
                 vBladePBladeIndex,
                 vBladeFrameIndex,
                 vBladeName,
                 egeneraTrapSeverity,
                 egeneraTrapMessage
             }
     STATUS      current
     DESCRIPTION
             "Encapsulates hardware events indicating intentional vBlade
             reboot.

             This trap is driven by 'Blade <framename>/p<1..24> non-sensor Event'
             event types that describe commanded reboots.

             Contact EES for more specific information.

             Since the underlying event type describes vBlade non-sensor hardware
             events, and since there are specific traps for panic, commanded shutdown,
             commanded reboot, and init level events, enabling/disabling this SNMP trap
             as an event action is bound to the enabling/disabling of vBladeHwEventTrap,
             vBladeCmdShutdownTrap, vBladeCmdHaltTrap, vBladePanicTrap, and
             vBladeInitTrap.

             Severity: 3"

        ::=     { vBladeNotifications 17 }


vBladePowerOnOpEvent NOTIFICATION-TYPE
    OBJECTS {
                vBladeIndex,
                vBladePBladeIndex,
                vBladeFrameIndex,
                vBladeName,
                egeneraTrapSeverity,
                egeneraTrapMessage
            }
    STATUS      current
    DESCRIPTION
            "Encapsulates vBlade power on operation event.

            This trap is driven by 'vBlade <framename>/c<1|2> Hardware Operation
            Event' event types.

            Since the underlying event type describes vBlade power on and off
            operation events, enabling/disabling this SNMP trap as an event action
            is bound to the enabling/disabling of vBladePowerOffOpEvent,
            vBladePowerCycleEvent, vBladeResetOpEvent, and vBladeNMIOpEvent.

            Severity: 5"

        ::=     { vBladeNotifications 26 }


vBladePowerOffOpEvent NOTIFICATION-TYPE
    OBJECTS {
                vBladeIndex,
                vBladePBladeIndex,
                vBladeFrameIndex,
                vBladeName,
                egeneraTrapSeverity,
                egeneraTrapMessage
            }
    STATUS      current
    DESCRIPTION
            "Encapsulates vBlade power off operation event.

            This trap is driven by 'vBlade <framename>/c<1|2> Hardware Operation
            Event' event types.

            Since the underlying event type describes vBlade power on and off
            operation events, enabling/disabling this SNMP trap as an event action
            is bound to the enabling/disabling of vBladePowerOnOpEvent,
            vBladePowerCycleEvent, vBladeResetOpEvent, and vBladeNMIOpEvent.

            Severity: 5"

        ::=     { vBladeNotifications 27 }


vBladePowerCycleOpEvent NOTIFICATION-TYPE
    OBJECTS {
                vBladeIndex,
                vBladePBladeIndex,
                vBladeFrameIndex,
                vBladeName,
                egeneraTrapSeverity,
                egeneraTrapMessage
            }
    STATUS      current
    DESCRIPTION
            "Encapsulates vBlade power cycle operation event.

            This trap is driven by 'vBlade <framename>/c<1|2> Hardware Operation
            Event' event types.

            Power cycle operations are currently not supported for vBlades.

            Since the underlying event type describes vBlade power on and off
            operation events, enabling/disabling this SNMP trap as an event action
            is bound to the enabling/disabling of vBladePowerOnOpEvent,
            vBladePowerCycleEvent, vBladeResetOpEvent, and vBladeNMIOpEvent.

            Severity: 5"

        ::=     { vBladeNotifications 28 }


vBladeResetOpEvent NOTIFICATION-TYPE
    OBJECTS {
                vBladeIndex,
                vBladePBladeIndex,
                vBladeFrameIndex,
                vBladeName,
                egeneraTrapSeverity,
                egeneraTrapMessage
            }
    STATUS      current
    DESCRIPTION
            "Encapsulates vBlade reset operation event.

            This trap is driven by 'vBlade <framename>/c<1|2> Hardware Operation
            Event' event types.

            Since the underlying event type describes vBlade power on and off
            operation events, enabling/disabling this SNMP trap as an event action
            is bound to the enabling/disabling of vBladePowerOnOpEvent,
            vBladePowerCycleEvent, vBladePowerCycleOpEvent, and vBladeNMIOpEvent.

            Severity: 5"

        ::=     { vBladeNotifications 29 }


vBladeNMIOpEvent NOTIFICATION-TYPE
    OBJECTS {
                vBladeIndex,
                vBladePBladeIndex,
                vBladeFrameIndex,
                vBladeName,
                egeneraTrapSeverity,
                egeneraTrapMessage
            }
    STATUS      current
    DESCRIPTION
            "Encapsulates vBlade reset operation event.

            This trap is driven by 'vBlade <framename>/c<1|2> Hardware Operation
            Event' event types.

            NMI operations are currently not supported for vBlades.

            Since the underlying event type describes vBlade power on and off
            operation events, enabling/disabling this SNMP trap as an event action
            is bound to the enabling/disabling of vBladePowerOnOpEvent,
            vBladePowerCycleEvent, vBladePowerCycleOpEvent, and vBladeResetOpEvent.

            Severity: 5"

        ::=     { vBladeNotifications 30 }


-- Compliance Statements

bladeFrameCompliance MODULE-COMPLIANCE
    STATUS      current

    DESCRIPTION
            "Requirements for conformance to the Host Resources MIB."

    MODULE -- this module

        MANDATORY-GROUPS {
                panManager, bladeFrames, devices, lPans, applications
        }

        ::= { adminInfo 1 }


END
